/*
 * Ferrix — SysML v2 model, part 14: the low-level requirements of object/.
 *
 * What each unit of src/kernel/src/object/ does, as `ItemLowLevel` requirements
 * (part 13 defines the format): the core ring's object layer -- what a handle
 * names and how it is dropped, channels, ports, interrupts, I/O mappings,
 * pins, the job quotas, jobs, the core half of a process, and the scoped OOM
 * kill. The handle table itself and the rights arithmetic are
 * `src/lib/kernel/objects` and `src/lib/proto/native-abi`, whose host tests verify
 * H.OBJ.1 to H.OBJ.4 directly; nothing here restates them.
 * L.object.253, reserved for init's grant of the memory scrub token to
 * memscrub, is released unwritten: the grant is ring-3 init's, outside the
 * item, and the item relies on nothing from it (ledger 5140 (3)).
 *
 * This is W-8's pilot (docs/certification/IMPLEMENTATION.md, step 3), the
 * subsystem the format was corrected on before the others copy it. What it
 * settled:
 *
 *  - one requirement per behaviour a check can pass or fail, and a
 *    requirement names every function that carries the behaviour as its
 *    `unit`, not one each: a write that is all or nothing is one sentence
 *    whatever number of functions make it so;
 *  - a requirement is no broader than one check can prove: a `Verifies:`
 *    tag credits the whole requirement, so every check that names one proves
 *    its whole criterion alone. Where the checks that exist each prove a
 *    part, the requirement is split, one part per check, and a part no check
 *    proves stays in the baseline as check-writing work -- never a tag
 *    crediting what its check does not test. The statement says no more than
 *    the criterion tests;
 *  - an accessor -- one statement or one expression, no branch and no
 *    `unsafe` -- needs no requirement of its own (check-traceability.py's
 *    rule); one is still named where it is the behaviour's entry point;
 *  - check code that lives in a product file is listed in
 *    tools/common/data/traceability-units.json, not given a requirement, and the
 *    requirement it would verify waits in the baseline until it moves into a
 *    check file where a `Verifies:` tag may go on it.
 *
 * Ids are `L.object.<n>`, numbered through the subsystem; the package gives
 * the file.
 */
package FerrixObjectRequirements {
    private import FerrixItemRequirements::*;

    package ObjectKinds {
        doc /* src/kernel/src/object/mod.rs: what a handle names, its signals, and
             * how objects are dropped without recursing. */

        requirement <'L.object.1'> aProcessHandleSaysTerminated : ItemLowLevel {
            attribute :>> statement = "Object::signals shall report a handle to a
                process TERMINATED once the process has ended and closed its
                handles.";
            attribute :>> criterion = "A handle to a process that has ended and
                closed its handles reports TERMINATED when waited on.";
            attribute :>> parent = "H.OBJ.11";
            attribute :>> unit = "object::Object::signals";
        }
        requirement <'L.object.2'> theOtherKindsSignals : ItemLowLevel {
            attribute :>> statement = "Object::signals shall report a port READABLE
                while it holds a packet, and no signal for a VMO, a device, an I/O
                mapping, a pin or the starter token.";
            attribute :>> criterion = "A wait for READABLE on a port holding a
                packet returns at once and on an empty port times out; a wait on
                each of a VMO, a device, an I/O mapping and a pin times out with 0
                signals observed.";
            attribute :>> parent = "H.OBJ.11";
            attribute :>> unit = "object::Object::signals";
        }
        requirement <'L.object.3'> waitersAreWokenAtTheChange : ItemLowLevel {
            attribute :>> statement = "Object::waiters shall name a channel end's
                own queue, which a message written to the end wakes, so that a wait
                on the end ends at the message and not at its deadline.";
            attribute :>> criterion = "A wait on a channel end with a two-minute
                deadline returns after a message written 20 ms later and before the
                deadline.";
            attribute :>> parent = "H.OBJ.11";
            attribute :>> unit = "object::Object::waiters";
        }
        requirement <'L.object.4'> disposeFreesWhatIsNested : ItemLowLevel {
            attribute :>> statement = "dispose shall drop every object it is given
                and every object those hold, a channel end's unread messages and the
                handles they carry included, so that nothing an object held outlives
                it.";
            attribute :>> criterion = "Closing both ends of a channel whose queue
                holds a VMO with a committed page gives that page back: the native
                checks' free-frame count is the same before and after, 0 frames
                kept.";
            attribute :>> parent = ("H.OBJ.16", "H.MEM.9");
            attribute :>> unit = ("object::dispose", "object::Object::drops_at_once");
        }
        requirement <'L.object.5'> disposeNeverRecurses : ItemLowLevel {
            attribute :>> statement = "dispose shall hold at most one queued
                object's drop on the stack at a time, however deeply objects are
                nested in one another's queues.";
            attribute :>> criterion = "A chain of N channel ends, each queued unread
                in the next's inbox, is freed from its outermost end with N in the
                thousands and no guard-page fault, every frame given back.";
            attribute :>> parent = ("H.OBJ.8", "H.FAIL.2");
            attribute :>> unit = ("object::dispose", "object::Object::drops_at_once");
        }
        requirement <'L.object.6'> aChannelEndClosesAtOnce : ItemLowLevel {
            attribute :>> statement = "dispose shall close a channel end whose last
                reference it holds before it returns, even while another context is
                draining disposed objects, so that the peer sees PEER_CLOSED from
                the moment the close returns (FX-1004).";
            attribute :>> criterion = "A close made while another context is marked
                as draining is followed at once by a write and a read on the peer,
                each refused PEER_CLOSED, 2 of 2.";
            attribute :>> parent = "H.OBJ.16";
            attribute :>> unit = "object::dispose";
        }
        requirement <'L.object.7'> nothingGivenUpWhileMemoryServes : ItemLowLevel {
            attribute :>> statement = "defer shall queue an object for the drainer
                and, when the queue cannot grow, drop it where it is while fewer
                than four such drops are under way, so that no object is given up
                while a drop in place is still allowed.";
            attribute :>> criterion = "Across the allocation-failure rounds, every
                nth fallible allocation failing for several n, 0 objects are given
                up (abandoned() reads 0) and every frame comes back.";
            attribute :>> parent = "H.MEM.11";
            attribute :>> unit = ("object::defer", "object::abandoned");
        }
        requirement <'L.object.8'> givenUpOnlyPastTheDepth : ItemLowLevel {
            attribute :>> statement = "defer shall give an object up, and count it,
                only when the queue cannot grow and four drops in place are already
                under way, and shall neither recurse further nor stop the kernel:
                the one exception to H.OBJ.8, an object that outlives its last
                handle, bounded by the depth and counted by abandoned().";
            attribute :>> criterion = "With the orphan queue refused its growth and
                four in-place drops nested, a fifth deferred object is counted as
                given up (abandoned() rises by 1) and the kernel runs on.";
            attribute :>> parent = "H.MEM.11";
            attribute :>> unit = "object::defer";
        }
        requirement <'L.object.105'> droppedInPlaceWithoutQueueRoom : ItemLowLevel {
            attribute :>> statement = "defer shall drop an object where it is, and
                give nothing up, when the orphan queue cannot grow and fewer than
                four drops in place are under way.";
            attribute :>> criterion = "A close of a job handle with the orphan
                queue's one growth refused answers success, the job is gone when it
                returns, and abandoned() stays 0.";
            attribute :>> parent = ("H.MEM.11", "H.OBJ.8");
            attribute :>> unit = "object::defer";
        }
    }

    package Channels {
        doc /* src/kernel/src/object/channel.rs. */

        requirement <'L.object.9'> aPairIsTwoObjects : ItemLowLevel {
            attribute :>> statement = "Endpoint::pair shall make two connected ends
                charged together as two objects to the running task's job, and shall
                make neither when the job's object limit refuses the charge.";
            attribute :>> criterion = "In a job limited to 5 objects and holding 5,
                a pair is refused; holding 3, a pair is made and the job holds 5;
                with everything dropped it holds 0.";
            attribute :>> parent = "H.QUOTA.3";
            attribute :>> unit = "object::channel::Endpoint::pair";
        }
        requirement <'L.object.10'> messagesReachThePeer : ItemLowLevel {
            attribute :>> statement = "A message written on one end of a channel
                shall be read, its bytes and the objects its handles name with the
                rights they carried, only on the other end, in the order written.";
            attribute :>> criterion = "Bytes and a VMO handle written by one process
                are read by the other as the same bytes and a handle through which
                the same VMO's contents are read.";
            attribute :>> parent = "H.OBJ.5";
            attribute :>> unit = ("object::channel::Endpoint::write",
                "object::channel::Endpoint::read", "object::channel::Side::other",
                "object::channel::Channel::half");
        }
        requirement <'L.object.11'> aRefusedTakeMovesNothing : ItemLowLevel {
            attribute :>> statement = "Endpoint::write shall answer a refusal of its
                take -- a handle the sender does not hold, or one named twice -- as
                the write's refusal, queueing nothing, so that every handle the
                write named stays with the sender.";
            attribute :>> criterion = "A send naming a good handle and one that does
                not exist is refused BAD_HANDLE and the good handle still works in
                the sender; a send of a channel end through itself is refused
                INVALID_ARGS.";
            attribute :>> parent = "H.OBJ.5";
            attribute :>> unit = "object::channel::Endpoint::write";
        }
        requirement <'L.object.12'> aWriteIsAllOrNothing : ItemLowLevel {
            attribute :>> statement = "Endpoint::write shall take the sender's
                handles out of its table only after the peer's queue has agreed to
                take the message, so that a write refused because the peer closed,
                the message is too big or the queue is full moves no handle.";
            attribute :>> criterion = "A write carrying a handle refused
                PEER_CLOSED, one refused TOO_BIG for its bytes and one refused
                SHOULD_WAIT for a full queue each leave the handle in the sender
                under the same value, usable: 0 handles taken by a refused write.";
            attribute :>> parent = "H.OBJ.5";
            attribute :>> unit = "object::channel::Endpoint::write";
        }
        requirement <'L.object.13'> aQueueIsBounded : ItemLowLevel {
            attribute :>> statement = "A channel end shall hold a bounded number of
                unread messages (channel::LIMITS, 256); a write to a full one shall
                be refused as full, and the writer shall not be told there is room
                until a read makes it.";
            attribute :>> criterion = "Writing to a reader that does not read is
                refused SHOULD_WAIT before 4097 messages are queued; the writer of
                the full channel is told neither that its peer has room nor
                WRITABLE; after draining it is told there is room, and its next
                write arrives. (That the bound is 256 exactly is the host tests' of
                the message queue, with the limit as a parameter.)";
            attribute :>> parent = "H.OBJ.10";
            attribute :>> unit = ("object::channel::Endpoint::write",
                "object::channel::Endpoint::peer_has_room",
                "object::channel::Endpoint::signals");
        }
        requirement <'L.object.14'> aReadThatDoesNotFitTakesNothing : ItemLowLevel {
            attribute :>> statement = "Endpoint::read shall leave a message queued,
                and report its size in bytes and handles, when the caller has room
                for fewer of either.";
            attribute :>> criterion = "A read with too little room for the bytes,
                then for the handle, is refused with the message's sizes both times,
                and a read with room then returns the message whole.";
            attribute :>> parent = "H.OBJ.7";
            attribute :>> unit = "object::channel::Endpoint::read";
        }
        requirement <'L.object.15'> anUndeliveredMessageGoesBack : ItemLowLevel {
            attribute :>> statement = "Endpoint::unread shall put a message the
                caller took and could not deliver back at the head of the queue and
                wake the end's waiters, so that the next read returns it.";
            attribute :>> criterion = "A message carrying an endpoint, read into a
                buffer that faults, is read whole by the next read with a good
                buffer, and the endpoint delivered is the one sent.";
            attribute :>> parent = "H.OBJ.7";
            attribute :>> unit = "object::channel::Endpoint::unread";
        }
        requirement <'L.object.16'> endpointsOnlyUnderTheTopologyLock : ItemLowLevel {
            attribute :>> statement = "Endpoint::read shall refuse, leaving it
                queued, a message that carries a channel end unless the caller holds
                the topology lock, so that no end is put back into a queue while a
                send's cycle walk runs.";
            attribute :>> criterion = "A message carrying an endpoint, read into
                buffers a fork still shares copy-on-write, is delivered whole after
                the delivery put it back and read again, and the fork keeps what it
                had.";
            attribute :>> parent = "H.OBJ.5";
            attribute :>> unit = ("object::channel::Endpoint::read",
                "object::channel::carries_endpoints");
        }
        requirement <'L.object.17'> anEmptyEndWithAClosedPeer : ItemLowLevel {
            attribute :>> statement = "Once its peer has closed, an end with nothing
                queued shall answer a read PEER_CLOSED, and a write to the peer
                shall be refused PEER_CLOSED.";
            attribute :>> criterion = "After the peer closes, while another context
                is marked as draining, a read and a write on the survivor are
                refused PEER_CLOSED, 2 of 2.";
            attribute :>> parent = "H.OBJ.16";
            attribute :>> unit = ("object::channel::Endpoint::read",
                "object::channel::Endpoint::peer_closed");
        }
        requirement <'L.object.18'> anEmptyEndWithAnOpenPeerSaysWait : ItemLowLevel {
            attribute :>> statement = "With nothing queued and its peer open,
                Endpoint::read shall report the queue empty, which the call answers
                SHOULD_WAIT.";
            attribute :>> criterion = "A read of an emptied channel end whose peer
                is open is refused SHOULD_WAIT.";
            attribute :>> parent = "H.OBJ.11";
            attribute :>> unit = "object::channel::Endpoint::read";
        }
        requirement <'L.object.19'> messagesBeforeTheCloseAreReadFirst : ItemLowLevel {
            attribute :>> statement = "Endpoint::read shall return every message the
                peer wrote before it closed before it answers PEER_CLOSED.";
            attribute :>> criterion = "A peer that writes 3 messages and closes
                leaves 3 to be read, in order, and only the fourth read answers
                PEER_CLOSED. A write and close between a read's look at the queue
                and its answer is argued in F-54 (the peer's close is looked at, with
                Acquire, before the queue), not shown by this check.";
            attribute :>> parent = "H.OBJ.16";
            attribute :>> unit = "object::channel::Endpoint::read";
        }
        requirement <'L.object.20'> closingAnEndFreesItsQueue : ItemLowLevel {
            attribute :>> statement = "Closing a channel end shall mark it closed
                under its queue's lock and free every message queued for it unread,
                with the objects they carry.";
            attribute :>> criterion = "A VMO queued unread in the closed end is
                freed: the native checks' free- frame count, taken around the check,
                is unchanged.";
            attribute :>> parent = ("H.OBJ.16", "H.MEM.9");
            attribute :>> unit = ("object::channel::Endpoint::drop",
                "object::channel::Endpoint::take_unread");
        }
        requirement <'L.object.21'> closingAnEndTellsItsPeer : ItemLowLevel {
            attribute :>> statement = "Closing a channel end shall fire the peer's
                registrations waiting for PEER_CLOSED.";
            attribute :>> criterion = "A registration for PEER_CLOSED on one end
                fires when the other end is closed, its packet carrying its key and
                PEER_CLOSED.";
            attribute :>> parent = "H.OBJ.17";
            attribute :>> unit = "object::channel::Endpoint::drop";
        }
        requirement <'L.object.22'> anEndsSignals : ItemLowLevel {
            attribute :>> statement = "Endpoint::signals shall report READABLE while
                a message is queued for the end and PEER_CLOSED once its peer has
                closed.";
            attribute :>> criterion = "A wait woken by a message reports the end
                READABLE, and a wait for PEER_CLOSED on an end whose peer has closed
                returns at once.";
            attribute :>> parent = "H.OBJ.11";
            attribute :>> unit = ("object::channel::Endpoint::signals",
                "object::Object::signals");
        }
        requirement <'L.object.23'> anEndsRegistrations : ItemLowLevel {
            attribute :>> statement = "Endpoint::observe shall fire a registration
                for READABLE or PEER_CLOSED at once when either already holds, and
                otherwise list it under the queue lock that the change it waits for
                is made under, so it is neither missed nor fired early.";
            attribute :>> criterion = "A registration on a readable end fires at
                once with its key; one on a quiet end fires on the next message, and
                one for PEER_CLOSED when the peer closes.";
            attribute :>> parent = "H.OBJ.17";
            attribute :>> unit = "object::channel::Endpoint::observe";
        }
        requirement <'L.object.24'> noCycleOfEnds : ItemLowLevel {
            attribute :>> statement = "check_carry shall find that a send carrying
                channel ends closes a cycle when the inbox it lands in is reachable
                from what it carries, following the ends queued in each inbox.";
            attribute :>> criterion = "Queueing one channel's end in another and
                then the second's in the first is refused, the refused send keeps
                its handle, and 0 frames of a VMO riding in the queue are kept.";
            attribute :>> parent = ("H.OBJ.8", "H.MEM.9");
            attribute :>> unit = ("object::channel::check_carry",
                "object::channel::queued_endpoints", "object::channel::identity",
                "object::channel::Endpoint::identity");
        }
        requirement <'L.object.25'> anEndQueuedTwiceIsNoCycle : ItemLowLevel {
            attribute :>> statement = "A send carrying an end whose inbox holds
                another end twice, by two handles to it, shall not be refused as a
                cycle or as a walk too long.";
            attribute :>> criterion = "With one end carried twice in an inbox, a
                send carrying that inbox's own end is taken.";
            attribute :>> parent = "H.OBJ.8";
            attribute :>> unit = "object::channel::queued_endpoints";
        }
        requirement <'L.object.26'> theWalkIsBounded : ItemLowLevel {
            attribute :>> statement = "A cycle walk shall visit at most 1024 queued
                ends, and a send whose walk would visit more shall be refused as too
                big, keeping what it would have carried with the sender.";
            attribute :>> criterion = "A send whose walk meets more queued ends than
                the bound is refused TOO_BIG and every handle it named is still the
                sender's.";
            attribute :>> parent = ("H.OBJ.10", "H.OBJ.5");
            attribute :>> unit = ("object::channel::check_carry",
                "object::channel::queued_endpoints");
        }
    }

    package Ports {
        doc /* src/kernel/src/object/port.rs. */

        requirement <'L.object.27'> aPortIsOneObject : ItemLowLevel {
            attribute :>> statement = "Port::new shall make an empty port charged as
                one object to the running task's job, and none when the job's object
                limit refuses the charge.";
            attribute :>> criterion = "In a job limited to 5 objects, exactly 5
                ports are made and the sixth refused; with them gone the job holds
                0.";
            attribute :>> parent = "H.QUOTA.3";
            attribute :>> unit = "object::port::Port::new";
        }
        requirement <'L.object.28'> userPacketsAreBounded : ItemLowLevel {
            attribute :>> statement = "Port::queue_user shall refuse a program's
                packet as full when 1024 of its packets are queued, whatever room
                signal packets have been promised.";
            attribute :>> criterion = "Filling a port nobody takes from is refused
                SHOULD_WAIT at exactly 1024 packets, and not before.";
            attribute :>> parent = "H.OBJ.10";
            attribute :>> unit = ("object::port::Port::queue_user",
                "object::port::Queue::push_fitting");
        }
        requirement <'L.object.29'> aPacketComesBackAsQueued : ItemLowLevel {
            attribute :>> statement = "Port::take shall return a user packet exactly
                as it was queued, and give back its share of the bound it was
                counted in.";
            attribute :>> criterion = "A queued user packet is taken with its key,
                its kind and both data words as queued.";
            attribute :>> parent = "H.OBJ.11";
            attribute :>> unit = ("object::port::Port::take",
                "object::port::Port::queue_user");
        }
        requirement <'L.object.30'> roomIsPromisedWhenRegistering : ItemLowLevel {
            attribute :>> statement = "A registration and an interrupt binding shall
                reserve room for their packet on the port when they are made, and be
                refused for memory then if it cannot be reserved, so that queueing a
                signal or interrupt packet never allocates and never finds the port
                without room.";
            attribute :>> criterion = "Across rounds of native calls with every nth
                allocation failing, every port reports 0 packets lost for want of
                room.";
            attribute :>> parent = ("H.MEM.11", "H.OBJ.17");
            attribute :>> unit = ("object::port::Port::promise",
                "object::port::Port::release_promise", "object::port::Promise::new",
                "object::port::Promise::drop", "object::port::Observer::new",
                "object::port::Port::queue_signal", "object::port::Queue::push_fitting");
        }
        requirement <'L.object.31'> anUndeliveredPacketGoesBack : ItemLowLevel {
            attribute :>> statement = "Port::put_back shall queue a packet the
                caller took and could not deliver ahead of every other, with its
                share of the bound, so that the next take returns it.";
            attribute :>> criterion = "A packet taken for a buffer that faults -- a
                user packet, a signal packet fired on a change and one fired as it
                was registered -- is returned by the next wait with a good buffer.";
            attribute :>> parent = "H.OBJ.7";
            attribute :>> unit = "object::port::Port::put_back";
        }
        requirement <'L.object.32'> aRegistrationFiresOnce : ItemLowLevel {
            attribute :>> statement = "A registration shall not fire before a signal
                it asked for is asserted, and shall fire once when one is, reporting
                it with its key, and not again.";
            attribute :>> criterion = "A registration does not fire before its
                signal, fires once on the message that asserts it with its key and
                READABLE, and a second write fires nothing.";
            attribute :>> parent = "H.OBJ.17";
            attribute :>> unit = ("object::port::trigger", "object::port::deliver",
                "object::port::Observer::fire", "object::port::register");
        }
        requirement <'L.object.33'> aChangeFiresOnlyWhatWantsIt : ItemLowLevel {
            attribute :>> statement = "trigger shall fire only the registrations
                whose signals the change asserts, leaving every other listed.";
            attribute :>> criterion = "A message fires the registration waiting for
                READABLE and not the one waiting for PEER_CLOSED listed ahead of
                it.";
            attribute :>> parent = "H.OBJ.17";
            attribute :>> unit = "object::port::trigger";
        }
        requirement <'L.object.34'> sixtyFourRegistrations : ItemLowLevel {
            attribute :>> statement = "register shall refuse a registration as full
                when the object already holds 64, counted after dropping those whose
                port has gone.";
            attribute :>> criterion = "The 65th registration on one object is
                refused SHOULD_WAIT; after its ports are closed the object takes 64
                again.";
            attribute :>> parent = "H.OBJ.10";
            attribute :>> unit = "object::port::register";
        }
    }

    package Interrupts {
        doc /* src/kernel/src/object/interrupt.rs. */

        requirement <'L.object.35'> aLineIsClaimedOnce : ItemLowLevel {
            attribute :>> statement = "Interrupt::new shall claim a line for at most
                one Interrupt at a time, and a line whose claim failed for memory
                shall be left free for the next claim.";
            attribute :>> criterion = "A second claim of a held line is refused
                ALREADY_BOUND; interrupt_create run once per allocation it makes,
                that one failing, claims the line or answers NO_MEMORY each time,
                and the next run claims it.";
            attribute :>> parent = ("H.IRQ.1", "H.IRQ.2");
            attribute :>> unit = ("object::interrupt::Interrupt::new",
                "object::interrupt::register_handler");
        }
        requirement <'L.object.36'> theLineIsFreedWithItsHolder : ItemLowLevel {
            attribute :>> statement = "Dropping the Interrupt that claimed a line
                shall free the line before the close returns, even while another
                context drains disposed objects, and a delivery in flight for the
                old holder shall not reach a new one.";
            attribute :>> criterion = "With a delivery taken and not yet fired, the
                holder's close lets the line be claimed again at once and the
                delivery then leaves the new holder quiet; a close made while
                another context drains lets it be claimed a third time.";
            attribute :>> parent = "H.IRQ.2";
            attribute :>> unit = ("object::interrupt::Interrupt::drop",
                "object::interrupt::Delivery::fire");
        }
        requirement <'L.object.37'> pendingUntilAcknowledged : ItemLowLevel {
            attribute :>> statement = "A delivery shall mark the line pending, and
                Object::signals report the interrupt READABLE, until
                Interrupt::acknowledge clears it.";
            attribute :>> criterion = "Before a delivery a wait on the interrupt
                times out; after one it sees READABLE; after interrupt_ack it times
                out again.";
            attribute :>> parent = "H.IRQ.2";
            attribute :>> unit = ("object::interrupt::take_delivery",
                "object::interrupt::on_interrupt", "object::interrupt::Line::fire",
                "object::interrupt::Interrupt::acknowledge",
                "object::interrupt::Delivery::fire",
                "object::Object::signals");
        }
        requirement <'L.object.38'> aDeliveryWakes : ItemLowLevel {
            attribute :>> statement = "Line::fire shall wake the tasks waiting on
                the interrupt and on the port it is bound to, after letting go of
                the interrupt-safe locks it took.";
            attribute :>> criterion = "In at least 5 of 8 rounds each way, a wait on
                the interrupt and a wait on its port are ended by the delivery's
                wake, not by the recheck timer.";
            attribute :>> parent = "H.IRQ.1";
            attribute :>> unit = ("object::interrupt::Line::fire",
                "object::Object::waiters");
        }
        requirement <'L.object.39'> aBoundInterruptQueuesOnePacket : ItemLowLevel {
            attribute :>> statement = "A bound interrupt shall queue one packet on
                its port, carrying its key, the interrupt kind and when it fired,
                each time it goes from quiet to pending, and Interrupt::bind shall
                refuse a second binding while the first port is held.";
            attribute :>> criterion = "A second bind is refused; two deliveries
                before the acknowledgement queue 1 packet with its key, kind and
                time, and a delivery after it queues another.";
            attribute :>> parent = "H.IRQ.1";
            attribute :>> unit = ("object::interrupt::Interrupt::bind",
                "object::interrupt::Line::fire", "object::port::Port::queue_interrupt",
                "object::port::Port::queue_from_interrupt");
        }
        requirement <'L.object.40'> aPendingInterruptIsQueuedWhenBound : ItemLowLevel {
            attribute :>> statement = "Interrupt::bind shall queue a packet at once
                for an interrupt that is already pending.";
            attribute :>> criterion = "An interrupt that fired while its port was
                gone queues its packet, with its new key and the interrupt kind, on
                a new port as it is bound.";
            attribute :>> parent = "H.IRQ.1";
            attribute :>> unit = ("object::interrupt::Interrupt::bind",
                "object::port::Port::queue_interrupt");
        }
        requirement <'L.object.41'> maskedFromDeliveryToAcknowledgement : ItemLowLevel {
            doc /* Rationale: an edge MSI-X vector's extra deliveries fold into the
                packet its holder has not answered, so masking it per delivery
                only cost two exits to the hypervisor per interrupt. The bound
                keeps interrupt time bounded: at most STORM_BOUND (64) handler
                runs per scheduling of the holder, where it was 1, each charged
                to the task the interrupt cut, so a storm costs other partitions
                up to that bound, accounted in their share
                (docs/certification/MEMORY-AND-TIMING.md §2.2; AoU-4, ASR-8). */
            attribute :>> statement = "A delivery shall mask a line the controller
                holds before it marks it pending, and acknowledge shall unmask it; a
                delivery shall leave an edge-triggered MSI-X vector unmasked unless
                more than STORM_BOUND (64) deliveries have reached it since the last
                acknowledgement, when it shall mask the vector's entry until the
                next acknowledgement; acknowledge shall clear pending before it
                unmasks, so a delivery after it queues a packet of its own; and a
                refused claim shall leave the holder's line unmasked.";
            attribute :>> criterion = "On an edge-triggered MSI-X vector: read at its
                entry the claimed line is unmasked and stays unmasked after a
                delivery; a delivery after the acknowledgement and before the drain
                queues a packet; after 64 unacknowledged deliveries the entry is
                still unmasked, after the 65th it is masked with the line's storm
                count one higher and one packet queued, and after the
                acknowledgement it is unmasked (the `irq` line).";
            attribute :>> parent = "H.IRQ.2";
            attribute :>> unit = ("object::interrupt::take_delivery",
                "object::interrupt::Line::hold_back",
                "object::interrupt::Interrupt::acknowledge",
                "object::interrupt::Interrupt::new",
                "device::Vector::coalesces", "device::Vector::reads_masked");
        }
        requirement <'L.object.42'> anUnheldLineIsMasked : ItemLowLevel {
            attribute :>> statement = "take_delivery shall mask at the controller a
                line no Interrupt holds and deliver nothing for it.";
            attribute :>> criterion = "A delivery on a line whose holder has let go
                wakes nobody, queues no packet, and leaves the line masked.";
            attribute :>> parent = "H.IRQ.3";
            attribute :>> unit = "object::interrupt::take_delivery";
        }
    }

    package IoMappings {
        doc /* src/kernel/src/object/io_mapping.rs. */

        requirement <'L.object.43'> wholePagesOrRefused : ItemLowLevel {
            attribute :>> statement = "IoMapping::new shall refuse an aperture that
                does not start on a page boundary or is not a whole number of
                pages.";
            attribute :>> criterion = "Every sub-page aperture the machine has (the
                virtio-mmio transports on ARMv7-A) is refused; 0 are mapped.";
            attribute :>> parent = "H.DMA.5";
            attribute :>> unit = ("object::io_mapping::IoMapping::new",
                "device::Aperture::whole_pages");
        }
        requirement <'L.object.44'> exactlyItsAperture : ItemLowLevel {
            attribute :>> statement = "IoMapping::map_into shall map exactly the
                aperture's pages, readable and writable, onto the device's own
                physical addresses.";
            attribute :>> criterion = "Each mapped page translates to the aperture's
                physical page at the same offset, and a forked child reaches the
                same device pages rather than copies.";
            attribute :>> parent = "H.DMA.5";
            attribute :>> unit = "object::io_mapping::IoMapping::map_into";
        }
    }

    package Pins {
        doc /* src/kernel/src/object/pin.rs. The budget's and the quarantine's
             * checks, P1 to P5 of docs/NVIDIA.md section 12.2, are in
             * object/pin/check.rs, a child module that may read what pin.rs
             * keeps to itself. Each device has a pin budget B, and live,
             * quarantined and kept counts against it, kept on its domain under
             * the quarantine's lock (NVIDIA N0f). The domain side of a pin is
             * iommu's (part 16). */

        requirement <'L.object.45'> aDeviceGetsExactlyItsPages : ItemLowLevel {
            attribute :>> statement = "A pin shall map exactly the held pages of the
                VMO into the device's domain and report each page's device address,
                in page order.";
            attribute :>> criterion = "A pin of two pages reports 2 addresses, each
                of which the domain translates to the VMO's page holding what the
                VMO holds.";
            attribute :>> parent = "H.DMA.3";
            attribute :>> unit = ("object::pin::Pin::with_budget", "object::pin::Pin::map",
                "object::pin::Pin::new", "object::pin::Pin::addresses");
        }
        requirement <'L.object.46'> unpinnedBeforeFreed : ItemLowLevel {
            attribute :>> statement = "Dropping a pin of a live owner shall take its
                pages out of the domain, the invalidation complete, before the hold
                on its frames is released; when the domain refuses, the frames
                shall be kept.";
            attribute :>> criterion = "On a translated domain a closed pin's pages
                are no longer reachable through the domain.";
            attribute :>> parent = "H.DMA.3";
            attribute :>> unit = ("object::pin::Pin::drop", "object::pin::keep");
        }
        requirement <'L.object.47'> aDeadDriversPinIsQuarantined : ItemLowLevel {
            attribute :>> statement = "Dropping a pin on a translated domain after
                its owner terminated shall keep its pages mapped and its frames
                held, charged to nobody, in the quarantine (on an untranslated
                domain too, with nothing to unmap: L.object.127), moving them from its
                device's live count to its quarantined count; a pin closed by a
                live owner shall not be quarantined, and its pages shall leave the
                live count.";
            attribute :>> criterion = "A 2-page pin closed by a dead process leaves
                the device 2 pages quarantined and 0 live; a pin closed by a live
                process leaves 0 live, 0 quarantined and 0 kept.";
            attribute :>> parent = "H.DMA.4";
            attribute :>> unit = ("object::pin::Pin::drop", "object::pin::quarantine",
                "object::pin::fold", "object::pin::unreserve");
        }
        requirement <'L.object.48'> twiceTheBudgetBoundsTheQuarantine : ItemLowLevel {
            attribute :>> statement = "A pin shall be refused QuarantineFull, with
                nothing counted, when its device's quarantined and live pages and
                its own would pass twice the device's budget.";
            attribute :>> criterion = "With a budget of 2 pages and nothing kept: a
                2-page pin is taken with 2 pages quarantined; a 1-page pin is
                refused with 4 quarantined; a 2-page pin is refused with 3
                quarantined.";
            attribute :>> parent = "H.DMA.4";
            attribute :>> unit = ("object::pin::reserve", "object::pin::Pin::with_budget");
        }
        requirement <'L.object.49'> theQuarantineGoesBackOnHello : ItemLowLevel {
            attribute :>> statement = "quarantine_release shall give back every
                quarantined pin of the device's domain, out of the domain first and
                then to the allocator, counting the pages written after their driver
                died, and take off the quarantined count exactly the pages it gave
                back; a pin whose unpin is refused shall move to the kept count,
                which counts against twice the budget for good.";
            attribute :>> criterion = "Of two 1-page quarantined pins, one refused
                its unpin: the release gives back 1 page and leaves 0 quarantined
                and 1 kept; a 2-page pin is then taken at a budget of 2; with 2
                more pages quarantined, a 2-page pin is refused QuarantineFull (1
                kept + 2 + 2 > 4).";
            attribute :>> parent = "H.DMA.4";
            attribute :>> unit = ("object::pin::quarantine_release",
                "object::pin::release", "object::pin::fold",
                "object::pin::account_release");
        }
        requirement <'L.object.118'> theBudgetIsTheDelegators : ItemLowLevel {
            attribute :>> statement = "device_set_limit shall set a device's pin
                budget only through a handle carrying SET_LIMIT, never while the
                device has live pins, and never so that twice every budget raised
                above the default would pass the ceiling, a quarter of RAM; a
                refusal shall change nothing. Every answer on a device handle
                shall be audited with the device, the limit, and the old and new
                values: a set as DEVICE_LIMIT_SET, a refusal as DEVICE_LIMIT with
                its status. device_get_limit shall answer the budget, the ceiling
                and the room.";
            attribute :>> criterion = "Without SET_LIMIT the set is ACCESS_DENIED;
                with a live pin, BAD_STATE; a budget whose double passes the room,
                NO_MEMORY, with the budget and the room read back unchanged; a set
                to the budget it has is taken; the ceiling read back is the
                kernel's, nonzero, and the room no more than it; and the audit
                record holds, for the checking process and the device, the three
                refusals with their statuses and the set, each naming the pin
                budget and its old and new values.";
            attribute :>> parent = ("H.DMA.4", "H.OBJ.2", "H.AUD.8");
            attribute :>> unit = ("object::pin::set_budget", "object::pin::raise_of",
                "object::pin::room", "object::pin::ceiling_room",
                "object::pin::count_ceiling", "object::pin::counts",
                "object::pin::budget_of", "syscall::native::device_set_limit",
                "syscall::native::set_limit_on", "syscall::native::device_and_rights",
                "syscall::native::device_get_limit", "audit::device_limit");
        }
        requirement <'L.object.119'> aPinPastTheBudgetIsRefused : ItemLowLevel {
            attribute :>> statement = "A pin shall be refused LimitReached, with
                nothing pinned and nothing counted, when its device's live pages and
                its own would pass the device's budget.";
            attribute :>> criterion = "With a budget of 2 pages, a 2-page pin is
                taken and counted 2 live, and a 1-page pin after it is refused
                LimitReached with the live count still 2.";
            attribute :>> parent = "H.DMA.4";
            attribute :>> unit = ("object::pin::reserve", "object::pin::Pin::new",
                "object::pin::announce");
        }
        requirement <'L.object.120'> liveIsReservedBeforeThePin : ItemLowLevel {
            attribute :>> statement = "A pin's pages shall be counted live under the
                quarantine's lock, in the step that tests the budget, before the
                domain maps them, and given back if the domain refuses.";
            attribute :>> criterion = "A page pinned twice into one domain is
                refused by the domain, and the live count is as before the refused
                pin.";
            attribute :>> parent = "H.DMA.4";
            attribute :>> unit = ("object::pin::Pin::with_budget", "object::pin::Pin::map",
                "object::pin::reserve", "object::pin::unreserve",
                "object::pin::PinBudget::write");
        }
        requirement <'L.object.126'> anUntranslatedLiveCloseGivesBack : ItemLowLevel {
            attribute :>> statement = "On an untranslated domain, dropping a pin of
                a live owner shall give its frames back at once and take its pages
                off the device's live count, keeping nothing: the device of such a
                domain reaches all of memory anyway (VULNERABILITY-ANALYSIS V-03,
                finding F-59).";
            attribute :>> criterion = "On an untranslated domain, six 2-page pins
                opened and closed in turn by a live process at a budget of 2 pages
                are each taken, leave the counts at 0 live, 0 quarantined and 0
                kept, and leave each frame with no reference but the check's.";
            attribute :>> parent = ("H.DMA.3", "H.DMA.4");
            attribute :>> unit = ("object::pin::Pin::drop", "object::pin::Pin::map",
                "object::pin::unreserve");
        }
        requirement <'L.object.127'> anUntranslatedDeadPinIsQuarantined : ItemLowLevel {
            attribute :>> statement = "On an untranslated domain, a pin dropped after
                its owner terminated shall go to the quarantine with its frames held
                and its pages counted quarantined, not kept, and the next HELLO its
                device's core accepts shall give it back.";
            attribute :>> criterion = "On an untranslated domain a 2-page pin closed
                by a dead process leaves 0 live, 2 quarantined and 0 kept with its
                frames still referenced; DeviceNode::hello_accepted then leaves the
                counts at 0 and each frame with no reference but the check's.";
            attribute :>> parent = "H.DMA.4";
            attribute :>> unit = ("object::pin::quarantine", "object::pin::quarantine_release",
                "object::pin::release", "device::DeviceNode::hello_accepted");
        }
        requirement <'L.object.194'> theIntelGpuBudgetIsTheKernels : ItemLowLevel {
            doc /* docs/INTEL-GPU.md section 5, K3; the consultant's K3 (2) and
                 * (3), ledger 2352. The kind is decided by what enumeration
                 * read (L.device.45), never by the driver, and the bound by
                 * the kernel, never by devmgr. */
            attribute :>> statement = "When the Intel integrated GPU's domain is
                made, before any pin is counted, its pin budget shall be set to
                min(4 GiB, (U - W) / 4) pages, U the frames the allocator manages
                and W the watermark, counted at stage 10; so the pages its pins
                hold, live, quarantined and kept, are at most twice that: at most
                half the usable RAM above the watermark, and at most 8 GiB.";
            attribute :>> criterion = "Stage 10's check reads this machine's
                budget as the formula gives it for its managed frames and
                watermark, at least 2 pages and at most half the frames above the
                watermark when doubled; the formula gives (4 Mi - 8192) / 4 pages
                for 16 GiB, the cap for 64 GiB and 0 with nothing above the
                watermark; a domain given it holds it with nothing counted, and
                its room is twice it.";
            attribute :>> parent = ("H.DMA.4", "H.OBJ.2");
            attribute :>> unit = ("object::pin::intel_gpu_budget_for",
                "object::pin::intel_gpu_budget", "object::pin::give_intel_gpu_budget",
                "object::pin::count_ceiling", "device::DeviceNode::domain");
        }
        requirement <'L.object.195'> theIntelGpuBudgetIsItsOwnBound : ItemLowLevel {
            attribute :>> statement = "A budget the kernel set for the Intel
                integrated GPU shall also be the most device_set_limit may set
                that device's budget to: past it the set shall be refused
                NO_MEMORY with nothing changed, under it the set shall be taken,
                and neither shall hold anything of the ceiling on raised budgets.";
            attribute :>> criterion = "On a domain given the Intel GPU's budget B,
                set_budget(B + 1) is refused PastCeiling with B kept, and
                set_budget(B - 1) is taken, answering B, with the ceiling's room
                unchanged.";
            attribute :>> parent = ("H.DMA.4", "H.OBJ.2");
            attribute :>> unit = ("object::pin::set_budget", "object::pin::bound_of",
                "object::pin::room", "object::pin::bounded");
        }
        requirement <'L.object.196'> theIntelGpuIsRefusedAtItsCap : ItemLowLevel {
            attribute :>> statement = "A pin of the Intel integrated GPU that would
                take its live pages past its budget shall be refused
                LIMIT_REACHED (ENOSPC), and one that would take its live,
                quarantined and kept pages past twice its budget refused
                QUARANTINE_FULL (EDQUOT), each with nothing pinned or counted;
                the pages it pins are those of a VMO, charged to the job that
                committed them.";
            attribute :>> criterion = "On a domain given the Intel GPU's budget B,
                with B - 1 pages live a one-page pin is taken and the next refused
                LimitReached; with 2B - 1 quarantined a one-page pin is taken and
                the next refused QuarantineFull; the counts after each refusal
                are those before it; QUARANTINE_FULL travels as EDQUOT and
                LIMIT_REACHED as ENOSPC.";
            attribute :>> parent = ("H.DMA.4", "H.OBJ.2");
            attribute :>> unit = ("object::pin::reserve", "object::pin::Pin::with_budget");
        }
    }

    package ChardevNodes {
        doc /* src/kernel/src/interfaces/chardev: the nodes a ring-3 driver
             * serves through the chardev core (docs/NVIDIA.md section 4.4),
             * and the Intel GPU's render-only node (docs/INTEL-GPU.md
             * section 4.2 and 4.4). The core is in the load ring; what the
             * item decides for it is DeviceNode::may_have_client_nodes. That a
             * render-only HELLO publishes renderD<N> from 128 alone, with no
             * minor of major 195 and no card (the consultant's K3 (1)), is the
             * load ring's, held by the same check. */

        requirement <'L.object.192'> noNodeForAnUntranslatedIntelGpu : ItemLowLevel {
            attribute :>> statement = "The chardev core shall refuse, as
                Untranslated and with nothing published, every HELLO for the
                Intel integrated GPU's function while its domain does not
                translate, or cannot be made, whatever minors it lists; a HELLO
                for any other function shall be judged as before.";
            attribute :>> criterion = "Stage 10's chardev check, the first PCI
                function taken as the Intel GPU and every domain as untranslated:
                HELLOs of the render node, and of nvidia0 and the render node,
                are each refused Untranslated, the kernel's end closed and the
                published minors and render nodes as before; the same function
                not taken as the Intel GPU has its render-only HELLO taken; on a
                machine whose PCI domains do not translate the Intel GPU's
                render-only HELLO is refused Untranslated on its own domain. With
                the refusal removed, the boot panics.";
            attribute :>> parent = "H.DMA.10";
            attribute :>> unit = "device::DeviceNode::may_have_client_nodes";
        }
    }

    package QuotaSlots {
        doc /* src/kernel/src/object/quota.rs: the counters behind FRU_RSA.1. */

        requirement <'L.object.50'> aChargeIsHierarchical : ItemLowLevel {
            attribute :>> statement = "quota::charge shall add to the slot and to
                every slot above it only if every level stays within its limit, and
                a charge refused at any level shall leave no level charged and count
                one refusal at the level whose limit refused it.";
            attribute :>> criterion = "For each of the four resources, with a child
                limited to 5 under a parent limited to 3, the fourth unit is
                refused, child, parent and root each read 3, and one refusal is
                counted at the parent and none at the child; with the parent
                unlimited the child takes 5 and refuses the sixth.";
            attribute :>> parent = ("H.QUOTA.5", "H.QUOTA.3");
            attribute :>> unit = ("object::quota::charge",
                "object::quota::uncharge_below", "object::quota::Resource::at",
                "object::quota::slot", "object::quota::record_refused");
        }
        requirement <'L.object.51'> anUnchargeComesBackExactly : ItemLowLevel {
            attribute :>> statement = "quota::uncharge shall take back exactly the
                amount from the slot and every slot above it, never below zero.";
            attribute :>> criterion = "A job charged and uncharged the same amount
                reads 0, and so does every level above it.";
            attribute :>> parent = "H.QUOTA.4";
            attribute :>> unit = ("object::quota::uncharge",
                "object::quota::uncharge_below");
        }
        requirement <'L.object.52'> aLimitReadsBackAndRefuses : ItemLowLevel {
            attribute :>> statement = "Quota::set_limit shall set the limit the next
                charge is judged against, and Quota::usage shall report the use, the
                limit and the refusals.";
            attribute :>> criterion = "pids.max and memory.max written through
                cgroupfs reach the job's quota and read back as written; an empty
                job reads 0 used and 0 refused. And with kernel objects alone, on every profile, the `core obj` line (object/rehome_check.rs::check_limits_and_usage).";
            attribute :>> parent = "H.QUOTA.5";
            attribute :>> unit = ("object::quota::Quota::set_limit",
                "object::quota::Quota::usage", "object::job::Job::set_limit",
                "object::job::Job::usage");
        }
        requirement <'L.object.53'> aSlotLivesWhileHeld : ItemLowLevel {
            attribute :>> statement = "A job's slot shall be held by its job, its
                child slots, each charge and each task that names it, and freed --
                letting go of its parent -- when the last hold goes.";
            attribute :>> criterion = "After the quota checks' jobs are gone the
                number of live slots is what it was before them: every slot given
                back.";
            attribute :>> parent = "H.QUOTA.4";
            attribute :>> unit = ("object::quota::claim", "object::quota::find_free",
                "object::quota::grow", "object::quota::hold", "object::quota::release",
                "object::quota::Quota::new", "object::quota::Quota::drop",
                "object::quota::hold_group", "object::quota::release_group");
        }
        requirement <'L.object.54'> aSlotIsClaimedClean : ItemLowLevel {
            attribute :>> statement = "claim shall hand out a slot, reused or new,
                with every use and refusal count at zero, every limit unlimited and
                the default weight.";
            attribute :>> criterion = "A job made on a slot another job freed after
                charging 5 of each resource under limits of 3 reads 0 used, 0
                refused and no limit for each, and weight 100.";
            attribute :>> parent = "H.QUOTA.4";
            attribute :>> unit = ("object::quota::claim", "object::quota::find_free");
        }
        requirement <'L.object.55'> aFrameIsChargedAPage : ItemLowLevel {
            attribute :>> statement = "charge_frame shall charge one page of memory
                to the slot and hold the slot, refusing when a limit would be
                passed, and uncharge_frame shall give back both.";
            attribute :>> criterion = "Faults in a job limited to 48 pages' worth
                are refused when the next page would not fit, the refusal counted,
                while a sibling faults 48 pages in; with the spaces gone every
                level's memory reads 0.";
            attribute :>> parent = ("H.QUOTA.2", "H.QUOTA.4");
            attribute :>> unit = ("object::quota::charge_frame",
                "object::quota::uncharge_frame");
        }
        requirement <'L.object.56'> kernelHeapIsMemory : ItemLowLevel {
            attribute :>> statement = "charge_kernel shall charge kernel heap
                against the memory limit and count it again as kernel memory, both
                or neither, and uncharge_kernel shall give back both.";
            attribute :>> criterion = "At a 32 KiB limit each kind of personality
                object is refused one past its count while a sibling makes one, and
                every byte charged comes back when they go. And with kernel objects alone, on every profile, the `core obj` line (object/rehome_check.rs::check_the_kernel_charge).";
            attribute :>> parent = "H.QUOTA.7";
            attribute :>> unit = ("object::quota::charge_kernel",
                "object::quota::uncharge_kernel", "object::quota::KernelHeap::charge",
                "object::quota::KernelHeap::uncharge");
        }
        requirement <'L.object.57'> aMoveBringsItsTasks : ItemLowLevel {
            attribute :>> statement = "charge_regardless shall add the amount to the
                slot and every slot above it whatever their limits say.";
            attribute :>> criterion = "A process moved into a job at its task limit
                of 8 is moved: the job reads 9 tasks and the job it left 1 fewer.";
            attribute :>> parent = "H.QUOTA.1";
            attribute :>> unit = "object::quota::charge_regardless";
        }
        requirement <'L.object.58'> chargingNobodyRestores : ItemLowLevel {
            attribute :>> statement = "charging_nobody shall run its work with no
                job charged for what it allocates, and restore the running task's
                job afterwards.";
            attribute :>> criterion = "Work run under charging_nobody in a job at
                its memory limit completes, the job's use is unchanged, and an
                allocation after it is charged to the job again.";
            attribute :>> parent = "H.QUOTA.2";
            attribute :>> unit = "object::quota::charging_nobody";
        }
        requirement <'L.object.59'> anObjectsChargeLivesWithIt : ItemLowLevel {
            attribute :>> statement = "A Charge shall be taken from the job when the
                object it pays for is made, refusing the object when a limit would
                be passed, and given back when the object is dropped.";
            attribute :>> criterion = "Objects in a job limited to 5 are refused at
                exactly 5, a channel's two ends together; with them dropped the job
                holds 0.";
            attribute :>> parent = ("H.QUOTA.3", "H.QUOTA.4");
            attribute :>> unit = ("object::quota::Charge::to",
                "object::quota::Charge::drop", "object::quota::Charge::running");
        }
        requirement <'L.object.60'> weightIsShared : ItemLowLevel {
            attribute :>> statement = "effective shall scale a task's weight, at
                each level from its job up, by the job's weight over the job's load,
                and adjust shall keep each job's load the weight of its runnable
                tasks and busy children.";
            attribute :>> criterion = "One spinning task alone in a job keeps about
                half a processor against eight in another job; with the tasks gone
                every job's load reads 0.";
            attribute :>> parent = "H.SCHED.3";
            attribute :>> unit = ("object::quota::effective", "object::quota::adjust");
        }
        requirement <'L.object.61'> theWeightIsSet : ItemLowLevel {
            attribute :>> statement = "Job::set_cpu_weight shall make the job's
                weight the value written.";
            attribute :>> criterion = "cpu.weight written 300 through cgroupfs reads
                back 300 from the job. And with kernel objects alone, on every profile, the `core obj` line (object/rehome_check.rs::check_the_weight).";
            attribute :>> parent = "H.SCHED.3";
            attribute :>> unit = ("object::quota::Quota::set_weight",
                "object::job::Job::set_cpu_weight", "object::job::Job::cpu_weight");
        }
        requirement <'L.object.62'> theWeightIsClampedAndPassedUp : ItemLowLevel {
            attribute :>> statement = "Quota::set_weight shall clamp the weight to 1
                to 10000, and change a busy job's contribution to its parent's load
                at once.";
            attribute :>> criterion = "A weight of 0 is stored as 1 and one of 20000
                as 10000; setting a busy job's weight changes its parent's load by
                the difference of the scaled weights.";
            attribute :>> parent = "H.SCHED.3";
            attribute :>> unit = ("object::quota::Quota::set_weight",
                "object::quota::Slot::reweigh");
        }
        // cpu.idle (docs/CGROUPS.md section 12): of the follow-ons
        // L.object.184-187 were reserved for; io.weight, the load ring's
        // (fs::blkio), claims nothing, so 186 went to the dentry and inode
        // caches' reclaim and 187 to the native weight an idle job refuses.
        requirement <'L.object.185'> anIdleJobHasTheIdleWeight : ItemLowLevel {
            attribute :>> statement = "A job with cpu.idle set shall have the
                entity weight 3, Linux's WEIGHT_IDLEPRIO, whatever its
                cpu.weight, and its cpu.weight's again once let off; setting or
                clearing it shall change a busy job's contribution to its
                parent's load at once.";
            attribute :>> criterion = "Two busy jobs of one task of weight 1024
                each, beneath one parent, run at 512 each; with one at
                cpu.weight 10000 and then set idle, the parent's load is 1027
                at once, the idle job's task runs at no more than 3 and its
                sibling's at more than 1000; let off, the parent's load and
                both tasks' weights are what they were at cpu.weight 10000
                (the cpu line of stage 13, object::quota::check_idle_weight). And with kernel objects alone, on every profile, the `core obj` line (object/rehome_check.rs::check_an_idle_job_weighs_little).";
            attribute :>> parent = "H.SCHED.3";
            attribute :>> unit = ("object::quota::Slot::entity_weight",
                "object::quota::Slot::reweigh", "object::quota::set_idle_at",
                "object::quota::Quota::set_idle", "object::quota::Quota::idle",
                "object::job::Job::set_cpu_idle", "object::job::Job::cpu_idle");
        }
        // The item's one refusal of cpu.idle: the native call's, beside
        // cgroupfs's cpu.weight, whose refusal is the load ring's and claims
        // nothing (the consultant's ruling, 2026-10-26, ledger line 10 of
        // this session's ledger).
        requirement <'L.object.187'> anIdleJobRefusesANativeWeight : ItemLowLevel {
            attribute :>> statement = "job_set_limit shall refuse a
                JOB_CPU_WEIGHT within 1 to 10,000 with BAD_STATE while the job
                has cpu.idle set, leaving its weight as it was, and shall take
                it once the job is let off.";
            attribute :>> criterion = "On a job at weight 250 set idle by
                Job::set_cpu_idle, job_set_limit of JOB_CPU_WEIGHT 400 answers
                BAD_STATE and job_get_quota reads 0, 250 and 0; let off, the
                same call answers 0 and job_get_quota reads 0, 400 and 0 (the
                native line's an_idle_job_refuses_a_weight).";
            attribute :>> parent = "H.SCHED.3";
            attribute :>> unit = ("syscall::native::job_set_limit",
                "object::job::Job::cpu_idle", "object::job::Job::set_cpu_idle");
        }
        requirement <'L.object.160'> theCarriedWeightIsTheWideFormula : ItemLowLevel {
            attribute :>> statement = "quota::effective shall carry a task's weight up
                its jobs in 64-bit arithmetic (ferrix_sched::carried_weight), giving,
                before it clamps the answer, the value the same formula gives in
                128-bit arithmetic, bit for bit, for every base and entity weight
                below 2^32 and every load.";
            attribute :>> criterion = "ferrix-sched's host test compares the two over
                50000 random and boundary bases, weights and loads at each job depth
                from 1 to 8, and at every weight 2^32 - 1, and finds no difference;
                with one division made in 32 bits, it finds one.";
            attribute :>> parent = "H.SCHED.3";
            attribute :>> unit = "object::quota::effective";
        }
        requirement <'L.object.161'> everyEntityWeightIsBelowTwoToThe32 : ItemLowLevel {
            attribute :>> statement = "Every entity weight a job can be given, its
                cpu.weight clamped to 1 to 10000 and scaled to task units, shall be
                below 2^32, as every task's weight, a u32, is.";
            attribute :>> criterion = "The kernel's build asserts that 10000 scaled
                to task units fits a u32; the quota check sets cpu.weight to 20000,
                reads 10000 back, and finds it scaled below 2^32.";
            attribute :>> parent = "H.SCHED.3";
            attribute :>> unit = ("object::quota::Quota::set_weight",
                "object::quota::Slot::entity_weight");
        }
    }

    package Tickets {
        doc /* src/kernel/src/object/ticket.rs: charging that follows the client
             * (docs/microkernel/K7.md; OPAQUE-KERNEL.md section 2 point 5; the
             * consultant's OK IF, ledger 2525). A ticket the kernel issues for
             * the caller's own job on one end of a channel, adopted by a server
             * thread through the other end. */

        requirement <'L.object.207'> aTicketNamesItsIssuer : ItemLowLevel {
            attribute :>> statement = "A ticket shall be issued only by
                charge_ticket ISSUE, for the process that makes the call and the
                job it is in, both read by the kernel; no operation shall take a
                job, a process or a quota slot; on an end shared by several
                processes each issue shall name its own issuer's job.";
            attribute :>> criterion = "A ticket issued by the client is adopted
                with the client's process id and job id, and a commit under it is
                charged to the client's job; one issued on the same end by a
                second process in job D is adopted with that process's ids and
                D's.";
            attribute :>> parent = "H.QUOTA.14";
            attribute :>> unit = ("object::ticket::Tickets::issue",
                "object::channel::Endpoint::issue_ticket",
                "object::process::Process::issuer_and_slot");
        }
        requirement <'L.object.208'> aTicketIsAdoptedFromThePeer : ItemLowLevel {
            attribute :>> statement = "charge_ticket ADOPT shall honour a ticket
                only through the other end of the channel it was issued on, and
                only while it is live; any other id shall be refused BAD_STATE,
                audited as TICKET, with the caller's adoption unchanged.";
            attribute :>> criterion = "An id never issued, an ended one, one
                issued on the adopting end and one issued on another channel are
                each refused BAD_STATE, the server's next commit is charged to its
                own job, and a TICKET record is kept for each.";
            attribute :>> parent = "H.QUOTA.14";
            attribute :>> unit = ("object::ticket::Tickets::find",
                "object::channel::Endpoint::adoptable_ticket",
                "object::channel::Side::index", "object::ticket::adopt");
        }
        requirement <'L.object.209'> anAdoptedCallChargesTheClient : ItemLowLevel {
            attribute :>> statement = "While a thread holds an adoption whose
                ticket is live, the VMO commits and pins and the new objects its
                native calls make shall be charged to the ticket's job and every
                job above it, against their limits; faults on its own space, its
                page tables and its kernel heap shall stay its own job's; a commit
                refused at the client's limit shall be answered NO_MEMORY with no
                throttle, no kill and no charge to the server's job.";
            attribute :>> criterion = "Under an adoption, four committed pages, a
                channel and a port raise the client's frames by four and objects
                by four and the server's by none, the client's heap unchanged; a
                read into the server's own fresh memory faults its pages in on the
                server; at the client's limit the commit is NO_MEMORY, neither
                job's high count moves, no process ends.";
            attribute :>> parent = "H.QUOTA.14";
            attribute :>> unit = ("object::quota::charge_target",
                "object::quota::charging_own", "object::ticket::charging_for_call",
                "mm::allocate_user_frame", "object::oom::fault_own",
                "object::oom::user_fault_own");
        }
        requirement <'L.object.210'> aTicketEndsForGood : ItemLowLevel {
            attribute :>> statement = "A ticket shall end at charge_ticket END
                from either end and when either end of its channel closes, never
                become live again, and its id never be issued again; a native
                call that starts after the end shall charge the calling thread's
                own job, with or without LEAVE; at most the rest of one call per
                adopted thread shall be charged to the client after the end,
                within the client's own limits.";
            attribute :>> criterion = "After the server's END, the client's END
                and the client's close, the server's next commit is charged to its
                own job with no LEAVE; every id issued in the check is greater
                than the one before.";
            attribute :>> parent = "H.QUOTA.14";
            attribute :>> unit = ("object::ticket::Tickets::end",
                "object::ticket::Tickets::end_all", "object::ticket::leave",
                "object::channel::Endpoint::end_ticket");
        }
        requirement <'L.object.211'> whatATicketChargedComesBack : ItemLowLevel {
            attribute :>> statement = "What a ticket charged shall stay charged
                to the client's job after the ticket ends, until the object goes,
                and shall then be taken back from exactly the levels it charged.";
            attribute :>> criterion = "A ticket's END leaves the client's frames
                as they were; once the server closes what it made and the
                processes are gone, the client's, the server's and their parent's
                frames and objects read zero.";
            attribute :>> parent = "H.QUOTA.14";
            attribute :>> unit = ("object::quota::Charge::to", "mm::release_frame");
        }
        requirement <'L.object.212'> ticketsAreBoundedPerEnd : ItemLowLevel {
            attribute :>> statement = "At most MAX_TICKETS (64) tickets shall be
                live on one end of a channel, the next ISSUE refused SHOULD_WAIT,
                and each ticket shall be one native object charged to its
                issuer's job.";
            attribute :>> criterion = "64 issues on one end raise the client's
                objects by 64, the 65th is refused SHOULD_WAIT, an END makes room
                for one more, and closing the channel gives every one back.";
            attribute :>> parent = "H.QUOTA.14";
            attribute :>> unit = "object::ticket::Tickets::issue";
        }
    }

    package JobReservations {
        doc /* A job's memory reservation (K12, docs/microkernel/K12.md §2.6):
             * who sets it, its rules, and its slot. */

        requirement <'L.object.221'> aReservationNeedsReserve : ItemLowLevel {
            attribute :>> statement = "job_set_limit with JOB_RESERVE shall need a
                handle with the RESERVE right, which no new object's handle
                carries; job_create shall give the new job's handle RESERVE only
                when the parent's handle has it; and process_create and
                job_create into a job that draws from a reservation shall be
                refused ACCESS_DENIED to a caller whose job draws from another,
                unless the handle carries RESERVE.";
            attribute :>> criterion = "Through the native calls, a reservation on a
                handle without RESERVE is refused ACCESS_DENIED, a duplicate
                adding RESERVE is refused, a job made beneath a reserved one
                through a handle without RESERVE from outside is refused, and one
                made through a handle with it carries it.";
            attribute :>> parent = "H.QUOTA.17";
            attribute :>> unit = ("syscall::native::job_reserve", "syscall::native::job_create",
                "syscall::native::process_create", "syscall::native::may_put_work",
                "object::job::Job::admits_work_from");
        }
        requirement <'L.object.222'> aReservationIsOneLevel : ItemLowLevel {
            attribute :>> statement = "A job shall be reserved for the first time
                only while nothing but the job holds its slot, under the lock a
                child slot is claimed under, and never with a reservation above
                or beneath it.";
            attribute :>> criterion = "At stage 9 a job beneath a reserved one and
                a job with a child are each refused a reservation.";
            attribute :>> parent = "H.QUOTA.17";
            attribute :>> unit = ("object::quota::Quota::set_reservation", "object::job::Job::set_reservation");
        }
        requirement <'L.object.223'> aReservationIsBesideItsLimit : ItemLowLevel {
            attribute :>> statement = "A job's reservation shall never exceed its
                own memory limit; no job above a reserved job shall carry a
                memory limit or memory.high; and a change that would break either
                shall be refused with nothing changed, cgroupfs answering EBUSY.";
            attribute :>> criterion = "At stage 9 a reservation above the job's own
                limit, under a memory limit and under a memory.high are each
                refused; once it is admitted, a limit and a memory.high above it
                and a limit below it are refused, and a limit at it is set.";
            attribute :>> parent = "H.QUOTA.17";
            attribute :>> unit = ("object::quota::Quota::set_limit",
                "object::quota::Quota::set_mark", "object::quota::limit_allowed",
                "object::quota::above");
        }
        requirement <'L.object.224'> aReservationReadsBack : ItemLowLevel {
            attribute :>> statement = "job_get_quota with JOB_RESERVE shall answer
                the reservation's size, what is drawn from it and the admissions
                refused it, in bytes; a set shall be audited LIMIT_SET and a
                refusal for want of memory LIMIT, both against resource 7.";
            attribute :>> criterion = "Through the native calls, a reservation of
                four pages and a byte reads back as four pages, nothing drawn and
                nothing refused.";
            attribute :>> parent = "H.QUOTA.16";
            attribute :>> unit = ("syscall::native::job_get_quota",
                "object::quota::Quota::reservation", "object::quota::Quota::refused",
                "audit::reservation_refused");
        }
        requirement <'L.object.225'> aReservationEndsWithItsSlot : ItemLowLevel {
            attribute :>> statement = "A slot claimed beneath a reserved job shall
                draw from its reservation, and a reserved job's slot, as its last
                hold goes, shall unbind its reservation. A writable btrfs mount,
                the other owner of a reservation, shall bind one as it is mounted,
                promising nothing until an operation asks, and unbind it when its
                volume is dropped, after its last operation; a mount that finds
                none free shall be mounted without one and say so.";
            attribute :>> criterion = "At stage 9 a job made beneath a reserved one
                draws from its reservation, and once the tree is gone the promise
                is what it was before and every slot is given back. At stage 12
                (fs::btrfs_write_check, reserve_check) the writable mount's
                reservation is bound and promises nothing between operations,
                the outstanding promise as before the mount; with every other
                entry bound a second mount of the disk is made without one; once
                unmounted and dropped, the mount's entry is unbound and the promise
                as before. Control: the mount's handle not unbinding in its drop
                (the entry stays bound).";
            attribute :>> parent = "H.QUOTA.15";
            attribute :>> unit = ("object::quota::claim", "object::quota::release",
                "object::quota::reservation_of");
        }
    }

    package Jobs {
        doc /* src/kernel/src/object/job.rs. */

        requirement <'L.object.63'> everyProcessInOneJob : ItemLowLevel {
            attribute :>> statement = "root shall answer the one job at the top of
                the tree, in which every process starts unless it is forked from a
                process elsewhere or moved.";
            attribute :>> criterion = "A new process is in the root job, and a
                fork's child in its parent's job.";
            attribute :>> parent = "H.OBJ.12";
            attribute :>> unit = ("object::job::root", "object::job::Job::new_tree_root",
                "object::job::Job::bare");
        }
        requirement <'L.object.64'> aChildsQuotaIsInsideItsParents : ItemLowLevel {
            doc /* The job's audit budget (docs/certification/AUDIT.md §3) is
                 * fixed here too, when the job is made: its own id, or its
                 * parent's where its maker says the job was its members' own
                 * to make (job::Budget), and written into its quota slot for
                 * the record of a refused charge. audit::check proves it. */
            attribute :>> statement = "A child job shall be made inside its parent,
                with a quota slot inside the parent's.";
            attribute :>> criterion = "A charge to a grandchild is counted in its
                parent and in the root of the check's tree too, and a limit on the
                parent refuses it.";
            attribute :>> parent = ("H.OBJ.12", "H.QUOTA.5");
            attribute :>> unit = ("object::job::Job::new_child",
                "object::job::Job::bare_child", "object::job::Job::new_root",
                "object::quota::Quota::identify");
        }
        requirement <'L.object.65'> aChildIsAnObjectAndRefusedWhenKilled : ItemLowLevel {
            attribute :>> statement = "A child job shall be charged as one object to
                the running task's job, and refused once its parent has been
                killed.";
            attribute :>> criterion = "In a job limited to 5 objects and holding 5,
                job_create is refused and nothing is charged; job_create in a killed
                job is refused.";
            attribute :>> parent = ("H.QUOTA.9", "H.OBJ.9");
            attribute :>> unit = ("object::job::Job::new_child",
                "object::job::Job::bare_child");
        }
        requirement <'L.object.66'> aNamedChildIsUnique : ItemLowLevel {
            attribute :>> statement = "Job::new_named_child shall refuse a name a
                named child of the job already has.";
            attribute :>> criterion = "A second child named a.slice beside the first
                is refused.";
            attribute :>> parent = "H.OBJ.12";
            attribute :>> unit = "object::job::Job::new_named_child";
        }
        requirement <'L.object.67'> theTreesLimits : ItemLowLevel {
            attribute :>> statement = "A new named child shall be refused when a job
                at or above its parent already holds as many descendants as its
                cgroup.max.descendants allows, or is more levels above it than its
                cgroup.max.depth allows.";
            attribute :>> criterion = "Under a job with cgroup.max.depth 1, a child
                is made and a grandchild refused Limited; under one with
                cgroup.max.descendants 2, a third descendant is refused.";
            attribute :>> parent = ("H.OBJ.12", "H.QUOTA.3");
            attribute :>> unit = ("object::job::Job::room_for_a_child",
                "object::job::Job::descendants", "object::job::Job::limits",
                "object::job::Job::walk");
        }
        requirement <'L.object.68'> rmdirKeepsALiveJob : ItemLowLevel {
            attribute :>> statement = "Job::remove_named_child shall refuse to
                remove a named child that holds a live anonymous job.";
            attribute :>> criterion = "rmdir of a cgroup holding a job native
                job_create made is refused EBUSY. And with kernel objects alone, on every profile, the `core obj` line (object/rehome_check.rs::check_a_busy_child_stays).";
            attribute :>> parent = "H.OBJ.12";
            attribute :>> unit = "object::job::Job::remove_named_child";
        }
        requirement <'L.object.69'> aRemovedJobTakesNothing : ItemLowLevel {
            attribute :>> statement = "A job remove_named_child has removed shall
                take no process and no child.";
            attribute :>> criterion = "Through a directory looked up before the
                rmdir, a move into the removed cgroup and a mkdir in it are each
                refused ENODEV, and the refused process stays where it was. And with kernel objects alone, on every profile, the `core obj` line (object/rehome_check.rs::check_a_removed_job_takes_nothing).";
            attribute :>> parent = "H.OBJ.12";
            attribute :>> unit = ("object::job::Job::remove_named_child",
                "object::job::Job::new_named_child", "object::job::Members::admits");
        }
        requirement <'L.object.70'> rmdirRefusedWhilePopulated : ItemLowLevel {
            attribute :>> statement = "Job::remove_named_child shall refuse to
                remove a named child that has a member not yet released or a named
                child of its own, and remove nothing.";
            attribute :>> criterion = "rmdir of a cgroup with one member is refused
                EBUSY and so is one with a child cgroup; after the member leaves and
                the child is removed, the rmdir succeeds.";
            attribute :>> parent = "H.OBJ.12";
            attribute :>> unit = "object::job::Job::remove_named_child";
        }
        requirement <'L.object.71'> theNoInternalProcessRule : ItemLowLevel {
            attribute :>> statement = "change_subtree_control shall enable only
                controllers offered and disable none a child still enables, and a
                job enabling a domain controller for its children shall admit no
                process.";
            attribute :>> criterion = "A controller not offered is refused; one a
                child enables cannot be disabled above it; a move into a job
                enabling a domain controller is refused, for a process counted in
                its job and for one that has left the count.";
            attribute :>> parent = "H.OBJ.12";
            attribute :>> unit = ("object::job::Job::change_subtree_control",
                "object::job::Members::admits", "object::job::Job::admits",
                "object::job::Job::subtree_control",
                "object::process::Process::move_charged");
        }
        requirement <'L.object.72'> whatCgroupfsSetsIsKept : ItemLowLevel {
            attribute :>> statement = "A job shall keep the owner, group and mode
                set for each of its cgroupfs nodes, the last set winning, and shall
                name its path from the root's child down, an anonymous job as
                job-<id>.";
            attribute :>> criterion = "A node's owner set twice reads as the second;
                a path names an anonymous job by number above its named child.";
            attribute :>> parent = "H.OBJ.12";
            attribute :>> unit = ("object::job::Job::set_node",
                "object::job::Job::path_names", "object::job::Job::display_name",
                "object::job::Job::children");
        }
        requirement <'L.object.73'> populatedIsCounted : ItemLowLevel {
            attribute :>> statement = "A job shall count its own members not yet
                released and its populated children, so that it is populated exactly
                while it or a job beneath it has a member not yet released, and each
                job whose state flips shall wake its waiters and fire its EMPTY
                registrations once no lock is held.";
            attribute :>> criterion = "A job with a member, and the job above it,
                are populated; each empties at its last member's release, not
                before, and wakes its event queue then and not while it stays
                populated.";
            attribute :>> parent = ("H.OBJ.12", "H.OBJ.11");
            attribute :>> unit = ("object::job::Job::count", "object::job::Job::count_in",
                "object::job::Job::count_out", "object::job::Job::count_in_checked",
                "object::job::Flipped::add", "object::job::notify",
                "object::job::Members::populated");
        }
        requirement <'L.object.74'> aJobsSignals : ItemLowLevel {
            attribute :>> statement = "A job shall assert EMPTY exactly while it is
                not populated, and Job::observe shall fire a registration for EMPTY
                at once if the job is empty and otherwise when it empties.";
            attribute :>> criterion = "EMPTY is asserted while the job is empty and
                not while it has a member; a registration for EMPTY fires at the
                last release and not the first, and one made while the job is empty
                fires at once. And with kernel objects alone, on every profile, the `core obj` line (object/rehome_check.rs::check_empty).";
            attribute :>> parent = "H.OBJ.11";
            attribute :>> unit = ("object::job::Members::signals",
                "object::job::Job::observe", "object::job::Job::signals",
                "object::Object::signals");
        }
        requirement <'L.object.75'> aKilledJobSaysTerminated : ItemLowLevel {
            attribute :>> statement = "Job::kill shall fire the job's registrations
                for TERMINATED, and the job shall report TERMINATED from then on.";
            attribute :>> criterion = "A registration for TERMINATED on a job fires
                when the job is killed, its packet saying what fired it, and a wait
                then sees the job TERMINATED.";
            attribute :>> parent = "H.OBJ.17";
            attribute :>> unit = ("object::job::Job::kill", "object::job::Members::signals",
                "object::job::Job::observe");
        }
        requirement <'L.object.76'> aKillEndsTheTree : ItemLowLevel {
            attribute :>> statement = "Job::kill shall mark the job and every job
                beneath it killed, fire their TERMINATED registrations, and end
                every process in them and none elsewhere; a job killed, or beneath
                one killed, shall refuse a new process or child from then on.";
            attribute :>> criterion = "Of 4 programs in a tree of three jobs and
                none, killing the middle job ends the middle and leaf programs with
                the kill's status and not the root's; killing the root ends it; the
                bystander finishes with its own status; a job beneath a killed one
                takes no new process.";
            attribute :>> parent = "H.OBJ.9";
            attribute :>> unit = ("object::job::Job::kill", "object::job::Job::walk",
                "object::job::Job::end_members", "object::job::Job::refuses",
                "object::job::Job::contains");
        }
        requirement <'L.object.77'> cgroupKillLeavesTheJob : ItemLowLevel {
            attribute :>> statement = "Job::kill_members shall end every process in
                the job and beneath it and leave every job as usable as it was.";
            attribute :>> criterion = "cgroup.kill ends the job's 1 member and
                leaves the job neither populated, killed nor dying, and a new member
                is taken.";
            attribute :>> parent = ("H.OBJ.12", "H.OBJ.9");
            attribute :>> unit = ("object::job::Job::kill_members",
                "object::job::Job::is_dying");
        }
        requirement <'L.object.78'> aForkIntoADyingJobEnds : ItemLowLevel {
            attribute :>> statement = "A process joining a job while a kill of
                either kind runs over it, or over a job above it, shall be ended, so
                that a loop of forks cannot outrun the kill.";
            attribute :>> criterion = "A program forking in a loop inside a job is
                ended with every child by one job_kill and by one cgroup.kill: 0
                processes of the job left running after either.";
            attribute :>> parent = "H.OBJ.9";
            attribute :>> unit = "object::job::Job::is_dying";
        }
        requirement <'L.object.79'> aChainOfJobsIsFreedIteratively : ItemLowLevel {
            attribute :>> statement = "Dropping the last reference to the deepest
                job of a chain shall free every job of it with one stack frame, not
                one per job.";
            attribute :>> criterion = "A chain of 10,000 jobs each holding the one
                above, built one reference at a time as a job_create and
                handle_close loop builds it, is freed from the deepest end with no
                guard-page fault.";
            attribute :>> parent = ("H.OBJ.8", "H.FAIL.2");
            attribute :>> unit = "object::job::Job::drop";
        }
        requirement <'L.object.80'> oomsAreCountedUpTheTree : ItemLowLevel {
            attribute :>> statement = "Job::count_oom shall count an OOM or an OOM
                kill in the job and in every job above it, and wake whatever polls
                their memory.events.";
            attribute :>> criterion = "After a scoped OOM kill, memory.events counts
                one OOM kill in the job and in its parent and none in a sibling, and
                an epoll on it is woken by the kill with EPOLLPRI. And with kernel objects alone, on every profile, the `core obj` line (object/rehome_check.rs::check_oom_counts). On Bare, present and desktop (bare_side_check): a_limit_ends_its_own.";
            attribute :>> parent = "H.QUOTA.6";
            attribute :>> unit = ("object::job::Job::count_oom",
                "object::job::Job::oom_counts");
        }
    }

    package Processes {
        doc /* src/kernel/src/object/process.rs: the core half of a process. */

        requirement <'L.object.81'> aProcessStartsCountedAndCharged : ItemLowLevel {
            attribute :>> statement = "Process::new shall make a process counted in
                its job and charged one task there; when the job's task limit
                refuses the charge it shall be marked over quota and charge
                nothing.";
            attribute :>> criterion = "A fork loop in a job limited to 8 tasks is
                refused at exactly 8, counting the forking process, the refusal
                counted as pids.events counts it, while a sibling job forks on.";
            attribute :>> parent = "H.QUOTA.1";
            attribute :>> unit = ("object::process::Process::new",
                "object::process::Process::over_quota");
        }
        requirement <'L.object.82'> aTableOf4096 : ItemLowLevel {
            attribute :>> statement = "Process::new shall give the process a handle
                table that holds at most HANDLE_LIMIT, 4096, handles.";
            attribute :>> criterion = "Duplicating into one process's table until it
                is refused ends in NO_HANDLES with at most 4096 held.";
            attribute :>> parent = "H.OBJ.7";
            attribute :>> unit = "object::process::Process::new";
        }
        requirement <'L.object.83'> tasksAreGivenBack : ItemLowLevel {
            attribute :>> statement = "A process shall give every task it charged
                back to its job once, when it is reaped or dropped.";
            attribute :>> criterion = "With the fork loop's processes and the
                process moved in gone, both jobs' task counts, and their parent's,
                read 0.";
            attribute :>> parent = ("H.QUOTA.1", "H.QUOTA.4");
            attribute :>> unit = ("object::process::Process::uncharge_tasks",
                "object::process::Process::drop");
        }
        requirement <'L.object.84'> aThreadIsATask : ItemLowLevel {
            attribute :>> statement = "Process::charge_thread shall charge the job
                one task for each thread beside the first, refused at the task
                limit, and Process::uncharge_thread shall give it back once as the
                thread goes.";
            attribute :>> criterion = "In a job limited to 3 tasks, a process makes
                2 threads and a third is refused EAGAIN; as the threads end the
                job's task count falls back to 1.";
            attribute :>> parent = ("H.QUOTA.1", "H.QUOTA.4");
            attribute :>> unit = ("object::process::Process::charge_thread",
                "object::process::Process::uncharge_thread");
        }
        requirement <'L.object.85'> aMoveCarriesItsTasks : ItemLowLevel {
            attribute :>> statement = "A move shall count the process in the new job
                and out of the old one, and carry its task charge with it.";
            attribute :>> criterion = "A process of a job with 2 tasks moved into a
                job at its limit of 8 leaves 9 tasks there and 1 behind.";
            attribute :>> parent = ("H.OBJ.12", "H.QUOTA.1");
            attribute :>> unit = ("object::process::Process::move_charged",
                "object::process::Process::move_to",
                "object::process::Process::move_new_to", "object::job::Job::adopt");
        }
        requirement <'L.object.86'> aRefusedMoveLeavesItWhereItWas : ItemLowLevel {
            attribute :>> statement = "A move refused because the destination, or a
                job above it, has been killed shall leave the process in its job.";
            attribute :>> criterion = "A move into a job beneath a killed one is
                refused and the process is still in the root job.";
            attribute :>> parent = "H.OBJ.12";
            attribute :>> unit = ("object::process::Process::move_charged", "object::job::Job::refuses",
                "object::job::Job::adopt");
        }
        requirement <'L.object.87'> aNewProcessMeetsTheTaskLimit : ItemLowLevel {
            attribute :>> statement = "Process::move_new_to shall refuse a process
                being made when the destination's task limit, or one above it, would
                be passed, leaving it where it was with nothing charged there.";
            attribute :>> criterion = "process_create into a job at its task limit
                is refused SHOULD_WAIT, the job's task count unchanged, and the
                refused process is not started.";
            attribute :>> parent = "H.QUOTA.8";
            attribute :>> unit = ("object::process::Process::move_new_to",
                "object::process::Process::move_charged");
        }
        requirement <'L.object.88'> leavingTheJobOnce : ItemLowLevel {
            attribute :>> statement = "Process::leave_job shall count the process
                out of its job exactly once, however often it is called.";
            attribute :>> criterion = "A released member is counted out once: the
                job's live count falls by exactly 1 per member released.";
            attribute :>> parent = "H.OBJ.12";
            attribute :>> unit = "object::process::Process::leave_job";
        }
        requirement <'L.object.89'> oneBootstrapOnce : ItemLowLevel {
            attribute :>> statement = "A process's bootstrap slot shall take one
                object and hand it over once, refusing a second give before the take
                and after it.";
            attribute :>> criterion = "A second give to one child is refused
                ALREADY_BOUND; the child's first process_bootstrap answers the end
                given with its rights and its second answers zero; a give after the
                take is refused ALREADY_BOUND. And with kernel objects alone, on every profile, the `core obj` line (object/rehome_check.rs::check_a_bootstrap_is_given_once).";
            attribute :>> parent = "H.OBJ.6";
            attribute :>> unit = ("object::process::Bootstrap::refusal",
                "object::process::Bootstrap::give", "object::process::Bootstrap::take");
        }
        requirement <'L.object.90'> anEndClosesTheSlot : ItemLowLevel {
            attribute :>> statement = "A bootstrap never taken shall be closed as
                its process ends, and the slot of an ended process shall refuse a
                give.";
            attribute :>> criterion = "A bootstrap never taken is closed as its
                holder ends, and its peer hears it; a give to an ended child is
                refused.";
            attribute :>> parent = "H.OBJ.6";
            attribute :>> unit = "object::process::Process::close_bootstrap";
        }
        requirement <'L.object.91'> anExecveSealsTheSlot : ItemLowLevel {
            attribute :>> statement = "Completing an execve shall seal a bootstrap
                slot nothing was given, and keep one given before it for the new
                program to take.";
            attribute :>> criterion = "After an execve with nothing given, a give is
                refused; one given before an execve is taken after it.";
            attribute :>> parent = "H.OBJ.6";
            attribute :>> unit = "object::process::Process::seal_bootstrap";
        }
        requirement <'L.object.92'> anUndeliveredBootstrapGoesBack : ItemLowLevel {
            attribute :>> statement = "Bootstrap::put_back shall hold again a
                bootstrap that was taken and could not be placed in the table.";
            attribute :>> criterion = "process_bootstrap into a full table is
                refused NO_HANDLES and the next process_bootstrap, with room,
                answers the handle given.";
            attribute :>> parent = ("H.OBJ.6", "H.OBJ.7");
            attribute :>> unit = "object::process::Bootstrap::put_back";
        }
        requirement <'L.object.104'> anUndeliveredBootstrapOfAnEndedProcessIsClosed : ItemLowLevel {
            attribute :>> statement = "Bootstrap::put_back shall hand a bootstrap
                that could not be placed back to be closed when the process has
                ended since it was taken.";
            attribute :>> criterion = "A bootstrap taken and not placed while its
                process ends is closed, and its peer hears it.";
            attribute :>> parent = ("H.OBJ.6", "H.OBJ.7");
            attribute :>> unit = "object::process::Bootstrap::put_back";
        }
        requirement <'L.object.93'> anEndFiresItsWatches : ItemLowLevel {
            attribute :>> statement = "Exit::close shall hand the registrations
                waiting for a process's end over to be fired, once, and a
                registration made afterwards shall fire at once.";
            attribute :>> criterion = "A watch registered while the process runs
                fires when it ends, and one registered afterwards fires at once,
                with its key.";
            attribute :>> parent = "H.OBJ.17";
            attribute :>> unit = ("object::process::Exit::close", "object::process::Exit::observe");
        }
        requirement <'L.object.94'> howItEndedIsKept : ItemLowLevel {
            attribute :>> statement = "A process's Exit shall report its status and
                the signal that ended it once it has terminated, and nothing
                before.";
            attribute :>> criterion = "process_status says running before the end,
                killed by SIGTERM for a process a signal ended, and exited with its
                code for one that exited. And with kernel objects alone, on every profile, the `core obj` line (object/rehome_check.rs::check_exit_reports_once_ended).";
            attribute :>> parent = "H.OBJ.11";
            attribute :>> unit = ("object::process::Exit::record", "object::process::Exit::status",
                "object::process::Exit::signal");
        }
        requirement <'L.object.95'> anUnstartedProcessEndsWithItsHandles : ItemLowLevel {
            attribute :>> statement = "A process made through the native ABI and
                never started shall be ended, with the kill's status, when the last
                handle to it goes.";
            attribute :>> criterion = "Closing an unstarted process's only handle
                ends it and it is freed; one whose handle rode unread in a channel
                ends when the channel is closed.";
            attribute :>> parent = "H.OBJ.8";
            attribute :>> unit = ("object::process::ProcessRef::created",
                "object::process::Control::drop", "object::process::Control::process",
                "object::process::downcast");
        }
        requirement <'L.object.96'> aHandleKeepsOnlyTheEnd : ItemLowLevel {
            attribute :>> statement = "A handle ProcessRef::new makes shall hold
                only how the process ended, and not the process.";
            attribute :>> criterion = "With nothing but a handle to it left, an
                ended process is freed.";
            attribute :>> parent = "H.OBJ.8";
            attribute :>> unit = "object::process::ProcessRef::new";
        }
        requirement <'L.object.97'> aStartedProcessIsHeldByItsTask : ItemLowLevel {
            attribute :>> statement = "Control::started shall let go of the
                reference that held a process nobody had started, so that once
                started the process is held by its task and not by the handles
                process_create made.";
            attribute :>> criterion = "A process made by process_create and started,
                which then exits, is freed while its creator still holds its handle,
                and the handle reports its status.";
            attribute :>> parent = "H.OBJ.8";
            attribute :>> unit = ("object::process::Control::started", "object::process::ProcessRef::created");
        }
        requirement <'L.object.98'> pidsAreCyclic : ItemLowLevel {
            attribute :>> statement = "allocate shall hand out the number after the
                last one handed out, skipping every number in use and wrapping past
                32767 to 300, and allocate_init shall hand out 1 only while no
                process holds it.";
            attribute :>> criterion = "Allocating through the range wraps to 300 and
                passes over a number still held; 0 numbers handed out twice.";
            attribute :>> parent = "H.OBJ.13";
            attribute :>> unit = ("object::process::allocate",
                "object::process::allocate_init", "object::process::name",
                "object::process::release_naming");
        }
        requirement <'L.object.99'> theLiveList : ItemLowLevel {
            attribute :>> statement = "live shall list every live process once,
                under its pid and not its threads' numbers, and drop its references
                with the table unlocked.";
            attribute :>> criterion = "A job kill, which finds its processes through
                live, reports exactly 1 process ended for a job with 1 member.";
            attribute :>> parent = ("H.OBJ.13", "H.OBJ.9");
            attribute :>> unit = "object::process::live";
        }
        requirement <'L.object.181'> aReapedPidFindsNothing : ItemLowLevel {
            attribute :>> statement = "Once unlist has been called for a process as
                it is reaped, find shall answer its pid with nothing and listed shall
                leave it out, while live still lists it and its pid stays taken
                until the process is dropped.";
            attribute :>> criterion = "A child reaped by wait4 and still held is
                found by none of kill(pid, 0), getpgid, getsid, pidfd_open, find
                and the listed processes, all ESRCH or absent, where before the
                reap each found it; object::process::live still lists it; its pid
                is not free until the process is dropped, and free after. A child
                let go by a parent that ignores SIGCHLD is found by neither
                kill(pid, 0) nor find, where before its end both found it. And with kernel objects alone, on every profile, the `core obj` line (object/rehome_check.rs::check_a_reaped_pid_finds_nothing).";
            attribute :>> parent = "H.OBJ.13";
            attribute :>> unit = ("object::process::unlist", "object::process::find",
                "object::process::listed", "object::process::gather");
        }
    }

    package OomKill {
        doc /* src/kernel/src/object/oom.rs, and the quota reading it starts from. */

        requirement <'L.object.100'> theKillIsScoped : ItemLowLevel {
            attribute :>> statement = "A user fault refused by a memory limit shall
                first take back clean file cache charged to the job whose limit was
                full or beneath it and retry the fault, and only when that gave
                back nothing end, with the kill's status (under a personality its signal), a process of that job or
                beneath it and none outside it, count the kill there, and retry the
                fault.";
            attribute :>> criterion = "A program writing 8 MiB in a job limited to 1
                MiB ends by SIGKILL, exactly 1 process killed, while a process with
                more resident memory in a sibling job lives; a read of a file past
                memory.max kills no process where the job's clean cache was room. On Bare, present and desktop (bare_side_check): a_limit_ends_its_own.";
            attribute :>> parent = ("H.QUOTA.6", "H.QUOTA.12");
            attribute :>> unit = ("object::oom::user_fault", "object::oom::out_of_memory",
                "object::oom::kill_within", "object::oom::at_or_above",
                "object::quota::at_limit");
        }
        requirement <'L.object.101'> theLargestIsChosen : ItemLowLevel {
            attribute :>> statement = "Among the live processes of the full job and
                the jobs beneath it, kill_within shall choose the one with the most
                resident pages, and never pid 1.";
            attribute :>> criterion = "With three processes of 1, 4 and 2 MiB
                resident in the full job, the one of 4 MiB is killed; with pid 1 the
                largest, the next largest is.";
            attribute :>> parent = "H.QUOTA.6";
            attribute :>> unit = ("object::oom::kill_within", "object::oom::at_or_above");
        }
        requirement <'L.object.102'> noLimitFullKillsMachineWide : ItemLowLevel {
            attribute :>> statement = "A fault that failed for want of memory with
                no limit full shall take back clean file cache anywhere and retry
                while that gave back any, at most MACHINE_RECLAIMS (16) times for
                one fault; once a reclaim gave back nothing or those are spent, it
                shall end, with the kill's status, the live process with the most
                resident pages anywhere, never pid 1, count the kill in that
                process's job and above and an OOM in none, and retry; it shall
                wait for a victim still ending, make no second machine-wide kill
                within KILL_GRACE_NANOS (250 ms) of one, kill nobody for a
                refusal the allocation check injected, and fail as it would
                without the OOM kill after MOST_ANSWERS (1024) answers to one
                fault.";
            attribute :>> criterion = "Stage 5's quota check, over three processes
                of its own in two jobs with 8, 32 and 1 pages resident and no limit
                set: with the injection armed nobody is killed; a fault's 1024th
                answer is a refusal; the process of 32 pages is killed, its job
                counts oom 0 and oom_kill 1 and the other job 0 and 0, and the
                answer is a retry; a second answer while it ends kills nobody;
                once it lets go its job's use falls by its 32 pages; within the
                grace a second kill is not made; after it the faulter, alone, is
                killed and told it is the victim.";
            attribute :>> parent = "H.QUOTA.22";
            attribute :>> unit = ("object::oom::out_of_memory", "object::oom::out_of_memory_at",
                "object::oom::fault", "object::oom::user_fault",
                "object::oom::machine_out_of_memory", "object::oom::machine_answer",
                "object::oom::machine_out_of_memory_among", "object::oom::kill_in",
                "object::oom::kill_victim", "object::oom::ended", "object::oom::survey",
                "object::oom::in_grace",
                "object::oom::machine_want",
                "fallible::injecting_here");
        }
        requirement <'L.object.103'> anEndedVictimIsEmptied : ItemLowLevel {
            attribute :>> statement = "A victim that has ended and closed
                everything, whose address space no live process shares and still
                holds pages -- which a release that unmapped it leaves none of
                (F-91) -- shall have that space handed by the next look at its
                full limit to the emptier (L.object.376), one space at a time,
                and emptied by it rather than at its parent's wait; a look that
                finds a victim still ending, or handed and not yet emptied, shall
                wait and retry, killing no second process, until it is emptied or
                its emptying is given up (L.object.375).";
            attribute :>> criterion = "Two faults at one full limit while the first
                victim is ending kill 1 process, and after the victim lets go the
                next fault retries and the job's memory use falls by the victim's
                resident pages, within a wait on that use of twice the emptier's
                patience, before its parent waits; the machine-wide kill's case
                the same (object::quota_check). Control: the emptier returning at
                once -- 'an ended victim's memory was not given back by the
                emptier before its parent's wait' (f107b3-c2).";
            attribute :>> parent = "H.QUOTA.6";
            attribute :>> unit = ("object::oom::kill_within",
                "object::oom::shared_with_the_living", "object::oom::ended");
        }
        // docs/OOM-REAPER.md section 2 (F-107's B; consultant ledger 8784, 8814).
        requirement <'L.object.374'> noKillEmptiesWhereAsked : ItemLowLevel {
            attribute :>> statement = "No OOM kill -- scoped, machine-wide or for
                the kernel's heap -- shall unmap a space where it was asked: the
                look shall hand an ended victim's space to the emptier, allocating
                nothing, a Weak in a slot behind a leaf lock and a wake.";
            attribute :>> criterion = "check-stack-depth, on all three
                architectures: no way by the calls the walk follows from
                object::oom::kill_in to AddressSpace::unmap or
                AddressSpace::empty_for_exit, nor from
                object::oom::hand_over to the kernel allocator's alloc or
                realloc, leaving out, each named in EMPTIES_NOTHING_STOPS with its
                reason: failure paths (a panic stops the machine); a switch (what
                runs after it belongs to another task); and a task's last reference
                let go (in the hand-off's wake the only waiter is the emptier, which
                never ends; anywhere else on the kill's walk a task's last drop is
                what drop_rest's row walks and bounds, F-104, L.mm.143). The tool's
                self-test has a case of each way. Control: ended's unmap put back
                -- the row's 'the OOM kill unmaps a space where it was asked' line
                (f107b-c1); an exit's emptying (AddressSpace::empty_for_exit) is
                a target too, held by the tool's self-test case (ledger 9611 X6). A
                victim's release that the kill's own stack would run, which the walk
                cannot see through the Host vtable, is L.object.377's.";
            attribute :>> parent = "H.QUOTA.6";
            attribute :>> unit = ("object::oom::hand_over");
        }
        requirement <'L.object.375'> aStalledEmptyingIsGivenUp : ItemLowLevel {
            attribute :>> statement = "A space handed to the emptier shall be given
                up once EMPTY_PATIENCE_NANOS (500 ms) pass with no chunk of it
                emptied, counted from its hand-off or its last chunk: marked on
                the space, said once on the console, passed over by every later
                look and holding back no later kill; an emptying whose chunks keep
                coming is never given up. A space given up while another takes the
                slot shall be marked at its own next look or the emptier's next
                wake, and no second space shall take the slot before it is.";
            attribute :>> criterion = "The emptier's case (object::quota_check,
                check_the_emptier), its gate shut: a victim handed and not emptied
                is waited for, and after the patience the look marks it given up
                and kills the next process in the job, 3 kills in all; its gate
                opened one chunk at a time, each after 300 ms, three chunks over
                more than the patience, the look waits at each and kills nobody
                else. Controls: the patience test removed -- 'a victim whose
                emptying did not come still held the kill past its patience'
                (f107b3-c3); progress never stamped, the patience counted from the
                hand-off -- 'an emptying giving pages back was given up'
                (f107b3-c4). The displacement path -- a stalled space given up
                while another takes the slot, marked at its own next look or the
                emptier's next wake -- is argued, not run (COVERAGE-RESIDUAL).";
            attribute :>> parent = "H.QUOTA.6";
            attribute :>> unit = ("object::oom::hand_over", "object::oom::victim_done",
                "user::space::AddressSpace::give_up_oom_emptying",
                "user::space::AddressSpace::oom_emptying_given_up");
        }
        requirement <'L.object.376'> theEmptierIsATaskOfItsOwn : ItemLowLevel {
            attribute :>> statement = "The emptier shall be a kernel task of its
                own, inside a reclaim for its whole life, so that no allocation it
                makes is answered by a reclaim or a kill; it shall empty a handed
                space a chunk at a time from the top -- the highest region's top
                EMPTY_CHUNK_PAGES (128) pages, splitting no region -- stamping
                progress only when a chunk lowered the highest region's end, and
                ending the space's emptying at a chunk that failed or lowered
                nothing, or once the space is given up or no longer handed.";
            attribute :>> criterion = "The emptier's case: after each chunk let
                through its gate the highest region's end has fallen and the count
                of regions has not risen, and after three the space has no region
                and the slot holds nothing; every chunk the emptier made was made
                inside a reclaim. Control: the reclaim mark not set at the
                emptier's start -- 'the emptier ran outside a reclaim'
                (f107b3-c5). check-stack-depth prints the emptier's row.";
            attribute :>> parent = "H.QUOTA.6";
            attribute :>> unit = ("object::oom::emptier", "object::oom::empty",
                "object::oom::let_go", "object::oom::in_slot",
                "object::oom::through_gate", "sched::start_reaper");
        }
        // docs/EXIT-TEARDOWN.md D2 (ledger 9611 X6, 9740 NR.1).
        requirement <'L.object.377'> anUnstartedVictimIsReleasedByTheEmptier : ItemLowLevel {
            attribute :>> statement = "A victim the OOM kill ends with no thread of
                it live shall not be released on the kill's own stack once the
                emptier runs: its release shall be owed to the emptier, which runs it
                before the victim's waiter is told, and no other victim shall be
                chosen until it has.";
            attribute :>> criterion = "Boot check (quota_check's
                check_an_unstarted_victim_is_released_by_the_emptier): a process of
                the check's own, never started and holding 32 pages, is chosen by a
                fault at its job's full limit; the kill returns with the victim
                ended and one release owed, the emptier runs it and lets its
                reference go, the victim's map is empty and its memory back, and the
                fault then goes in. Control: the owing made false (owe_release's
                emptier test never true) -- 'an unstarted victim's release ran on its
                kill's own stack' (FX panic). Residuals, as built: before the emptier
                has named itself at boot the release runs at once, as before; an
                owed release may sleep on the victim's layout lock while the asker
                holds it, which the asker's own retries bound (MOST_ANSWERS, and
                KERNEL_HEAP_ANSWERS for the kernel's heap); while a release is owed,
                every kill answers retry.";
            attribute :>> parent = "H.QUOTA.6";
            attribute :>> unit = ("object::oom::owe_release",
                "object::oom::release_owed_pending",
                "object::bare::Bare::release_owed");
        }
        requirement <'L.object.106'> cpuIsChargedUp : ItemLowLevel {
            attribute :>> statement = "charge_cpu shall charge the time a task ran
                to its job and every job above it and to the machine, counted in
                their cpu.stat by the time cpu.stat is read, as user time when the
                tick that ended the slice interrupted user mode and as system time
                otherwise, and throttled_until shall report a job whose subtree has
                used its cpu.max quota and what cpu.max.burst carried into this
                period (L.object.184), as throttled until the period ends.";
            attribute :>> criterion = "A program of two counting threads in a job
                with cpu.max 20000 100000 is held to between a twelfth and two
                thirds of a processor, its cpu.stat counts at least 3 throttled
                periods and its user and system time add to its usage, and with
                cpu.max max it takes more than six tenths. On Bare, present and desktop (bare_side_check): the tree's charges and periods on a spinner, a_quota_cuts_a_program_alone; the tick's user-or-system half is L.sched.80's.";
            attribute :>> parent = "H.QUOTA.10";
            attribute :>> unit = ("object::quota::charge_cpu",
                "object::quota::throttled_until", "object::quota::refresh_period",
                "object::quota::runtime_left", "object::quota::Quota::set_bandwidth",
                "object::quota::charge_bandwidth");
        }
        // cpu.max.burst (docs/CGROUPS.md section 12): the first of the
        // follow-ons L.object.184-187 were reserved for; 185 is cpu.idle's,
        // 186 the dentry and inode caches' reclaim's, 187 the native weight
        // an idle job refuses.
        requirement <'L.object.184'> burstCarriesUnusedQuota : ItemLowLevel {
            attribute :>> statement = "When a period under a cpu.max quota ends,
                refresh_period shall carry into the next the runtime the period
                left unused, its quota and what it carried less what it used, up
                to the lesser of the job's cpu.max.burst and its quota, and
                nothing with no burst, first storing the most that can be
                carried so that a charger in between is never throttled short
                of its runtime; a job's runtime in a period shall be its quota
                and what was carried, for charge_bandwidth, throttled_until and
                runtime_left; and a period that used more than its quota under
                a burst shall count one in nr_bursts and in burst_usec what it
                used beyond the quota, up to its runtime. set_burst shall store
                the job's burst and drop what was carried.";
            attribute :>> criterion = "On a slot under a quota of 20 ms a 100
                ms period with a burst of 20 ms, charged at chosen instants: a
                period that used 5 ms leaves the next 35 ms (20 ms once the
                burst is written again, the carry then put back); 30 ms of use
                there
                neither throttles nor counts a throttle, and 36 ms throttles
                until that period's end; the period after has 20 ms, with one
                burst of 15 ms counted, and 21 ms of use there counts no burst;
                and with the burst at 0 a period that used 5 ms carries nothing
                (the cpu line of stage 13, object::quota::check_burst_carry). And with kernel objects alone, on every profile, the `core obj` line (object/rehome_check.rs::check_a_burst_is_carried).";
            attribute :>> parent = "H.QUOTA.10";
            attribute :>> unit = ("object::quota::carry", "object::quota::carry_bound",
                "object::quota::carry_cap", "object::quota::allowance",
                "object::quota::Quota::set_burst", "object::quota::set_burst_at");
        }
        requirement <'L.object.107'> aFrozenProcessParks : ItemLowLevel {
            attribute :>> statement = "sync_freeze shall set a process frozen when
                its job or one above it has cgroup.freeze set, whether the freeze
                came before the process was made, before it was moved in, or after
                it was running, and a frozen process shall report is_frozen until
                its job is thawed, which under a personality SIGCONT does not do.";
            attribute :>> criterion = "A program of three threads in a frozen
                cgroup stops counting and reports frozen through cgroup.events; a
                fork made in it, a process moved into it and one made by clone3 into
                it start frozen; SIGCONT leaves it frozen; one moved out of it is
                not. On Bare, present and desktop (bare_side_check): sync_freeze on Bares born, moved and thawed, a_job_says_who_is_frozen; the parking and SIGCONT are the load check above.";
            attribute :>> parent = "H.QUOTA.11";
            attribute :>> unit = ("object::process::Process::sync_freeze",
                "object::process::Process::is_frozen", "object::job::Job::freezing",
                "object::job::Job::set_freeze", "object::job::Job::note_frozen");
        }
        requirement <'L.object.108'> memoryHighReclaims : ItemLowLevel {
            attribute :>> statement = "throttle shall, for a program that just took
                a page while its job or one above is over its memory.high, take
                back clean cache from that job down to the mark, count the crossing
                in memory.events high in the job whose mark it was and above, and
                pause a millisecond if that gave back less than the excess.";
            attribute :>> criterion = "A cgroup reading a file twice its memory.high
                holds no more than the mark afterwards, memory.events counts the
                crossing, and a second read takes more. On Bare, present and desktop (bare_side_check): over_its_mark_a_job_gives_back; the millisecond's pause is the load check's.";
            attribute :>> parent = "H.QUOTA.12";
            attribute :>> unit = ("object::oom::throttle", "object::quota::over_high",
                "object::quota::count", "object::quota::bump", "object::quota::Counter::at",
                "object::job::Job::wake_memory_events");
        }
        requirement <'L.object.109'> reclaimIsScoped : ItemLowLevel {
            attribute :>> statement = "reclaim shall give back clean cache pages of
                disk files whose frame is charged to the job it is asked at or
                beneath it, never a sibling's and never a child's at or under its
                memory.min, and every page it gave back shall read as its source
                has it.";
            attribute :>> criterion = "Reclaim at one cgroup leaves a sibling's
                cached file untouched, spares a child using no more than its
                memory.min, and what it took reads back as the source has it. And with kernel objects alone, on every profile, the `core pc` line (user/rehome_cache_check.rs::check_reclaim_is_scoped).";
            attribute :>> parent = "H.QUOTA.12";
            attribute :>> unit = ("user::cache::reclaim", "user::cache::reclaim_pages",
                "user::cache::take_from",
                "user::cache::takes", "object::quota::protected",
                "user::vmo::Vmo::reclaim_clean", "user::vmo::Vmo::take_clean_range",
                "object::quota::within",
                "object::job::Job::mark", "object::quota::Quota::set_mark",
                "object::quota::Mark::at", "user::cache::register", "user::cache::live",
                "user::vmo::Vmo::reclaimable", "user::vmo::Vmo::pick_pages",
                "user::vmo::Vmo::for_each_page");
        }
        requirement <'L.object.110'> aGoneJobStaysGone : ItemLowLevel {
            attribute :>> statement = "job_ended shall be true for a quota slot from
                the moment its job goes, though a task still holds the slot, and
                false again once the slot is claimed anew, so that state kept per
                slot is not started for a job that has gone.";
            attribute :>> criterion = "A task of a cgroup that was removed under it
                reads the disk, and the quota slots in use are back to what they
                were before the cgroup. And with kernel objects alone, on every profile, the `core obj` line (object/rehome_check.rs::check_a_slot_says_its_job_went).";
            attribute :>> parent = "H.QUOTA.4";
            attribute :>> unit = ("object::quota::job_ended", "object::quota::on_job_release");
        }
        requirement <'L.object.111'> theCacheIsCounted : ItemLowLevel {
            attribute :>> statement = "resident shall count the pages of cached
                files charged to a job and the jobs beneath it, apart from those
                of memory filesystems, for memory.stat's file and shmem.";
            attribute :>> criterion = "memory.stat's file equals the cache that
                memory.current holds, and its shmem the memory filesystem's. And with kernel objects alone, on every profile, the `core pc` line (user/rehome_cache_check.rs::check_resident).";
            attribute :>> parent = "H.QUOTA.12";
            attribute :>> unit = "user::cache::resident";
        }
        requirement <'L.object.112'> anEvictedPageIsNoHole : ItemLowLevel {
            attribute :>> statement = "A page of a disk file that was filled
                before a private mapping's fault took its lock and was reclaimed
                since shall not be copied or read as zeros: copy_or_zero shall
                hand the frame back and ask for the fault to be made again, and
                read_present shall answer that the page is absent.";
            attribute :>> criterion = "A page reclaim took reads back as the
                source has it, never as zeros, through a read and through a
                fault. And with kernel objects alone, on every profile, the `core mem` line (user/rehome_check.rs::check_a_fill_reclaimed_is_filled_again).";
            attribute :>> parent = "H.QUOTA.12";
            attribute :>> unit = ("user::space::copy_or_zero", "user::vmo::Vmo::read_present");
        }
        // memory.stat's pagetables and anon (docs/CGROUPS.md section 10): the
        // follow-on of stage 13 L.object.182 was reserved for.
        requirement <'L.object.182'> tablesAreCountedApart : ItemLowLevel {
            attribute :>> statement = "ChargedTables::allocate_table shall
                charge a program's page table as charge_table does, as memory
                and again as Resource::Tables, and mark its frame record with
                TABLE_OWNER beside its job's slot; a frame's free shall take back,
                through uncharge_owner, a table's charge, memory and
                Resource::Tables, for a frame so marked, and a page's otherwise.";
            attribute :>> criterion = "A job's program that faults 4 pages of a
                fresh anonymous mapping has memory.stat's anon at least those 4
                pages and pagetables at least one page, and anon, file, kernel,
                pagetables and shmem add to memory.current; unmapping it gives
                back exactly the 4 pages from anon and some of pagetables (the
                reclaim line of stage 13 that names pgfault). And with kernel objects alone, on every profile, the `core obj` line (object/rehome_check.rs::check_a_table_is_charged_as_a_table).";
            attribute :>> parent = ("H.QUOTA.2", "H.QUOTA.4");
            attribute :>> unit = ("object::quota::charge_table",
                "object::quota::uncharge_table", "mm::uncharge_owner",
                "mm::ChargedTables::allocate_table");
        }
        // memory.reclaim (docs/CGROUPS.md section 10): the follow-on of stage
        // 13 that L.object.182-183 were reserved for.
        requirement <'L.object.183'> memoryReclaimGivesBackWhatIsAsked : ItemLowLevel {
            attribute :>> statement = "reclaim_asked shall give back the bytes
                of the pages it is asked for, charged to the scope or beneath
                it, as the pages and the heap reclaim at that scope answers
                (L.object.186), in rounds of at most 32 pages' worth; it shall
                answer Short once more than 16 rounds, in all, gave back
                nothing, neither page nor heap, short of the count, Interrupted
                when asked to stop between rounds, and Short for any count but
                zero at no scope, which would be the whole machine.";
            attribute :>> criterion = "A cgroup holding 64 pages of a file's
                cache and 4 of a tmpfs file, beside a sibling holding 8, gives
                back nothing for a write of 0, at least 32 pages for a write of
                32 pages' bytes, and all its file cache and none of its tmpfs
                pages for a write of 1G, which is EAGAIN; max is EINVAL; the
                sibling keeps its 8 pages; the file reads as its source has it
                after; a reclaim of 32 pages interrupted before its first round
                takes none; and at no scope a count of 1 is Short and of 0 is
                Given; and a cgroup with no cache, after 64 misses, gives back a
                write of 8192 bytes from its cached dentries (the `reclaim`
                line of stage 13 that names memory.reclaim and cached
                dentries). And with kernel objects alone, on every profile, the `core pc` line (user/rehome_cache_check.rs::check_reclaim_asked) and the `core shr` line (user/rehome_cache_check.rs::check_the_shrinker).";
            attribute :>> parent = "H.QUOTA.12";
            attribute :>> unit = "user::cache::reclaim_asked";
        }
        requirement <'L.object.188'> reclaimTakesOnlyCleanPages : ItemLowLevel {
            attribute :>> statement = "reclaim shall give back a page of a disk
                file only through reclaim_clean: only the pages the file's source
                hands it, and of those only a page Clean at the take, looked at under
                the pages lock the take is made under; a page written, by write or
                through a shared mapping, and not yet written back shall stay and
                read back as last written.";
            attribute :>> criterion = "On a writable btrfs mount a file synced
                and then written again in one page loses its clean pages to a
                reclaim of the whole cache, keeps the written one, and reads back
                as it was last written, every page; a shared mapping that may
                write, made and written between the source's answer and the
                take, keeps the page it wrote, and the write reads back through the
                file (the `reclaim` line of test-btrfs). And with kernel objects alone, on every profile, the `core pc` line (user/rehome_cache_check.rs::check_a_written_page_stays, user/rehome_cache_check.rs::check_a_mapping_made_at_the_take).";
            attribute :>> parent = "H.QUOTA.12";
            attribute :>> unit = ("user::cache::take_from", "user::vmo::Vmo::reclaim_clean",
                "user::vmo::reclaim_clean", "user::vmo::Vmo::decommit_clean_range",
                "user::vmo::Vmo::take_clean_range", "user::vmo::Vmo::take_range_if",
                "user::vmo::Pages::take_clean_into", "user::vmo::Vmo::decommit_in_chunks");
        }
        // The dentry and inode caches as reclaimable (docs/CGROUPS.md
        // section 10): the follow-on of stage 13 M1's note left open, in
        // the id the io controller's reservation released.
        requirement <'L.object.186'> reclaimAsksTheShrinkerForTheRest : ItemLowLevel {
            attribute :>> statement = "reclaim shall, when the pages it gave
                back are fewer than it was asked for, ask the registered
                shrinker for the rest in bytes, naming to it only the jobs at
                the scope or beneath it, and shall answer the bytes the
                shrinker gave back apart from the pages.";
            attribute :>> criterion = "A cgroup that looked up 64 names that
                are not there, beside a sibling that did the same, holds their
                negative dentries in memory.stat's kernel; a write of 1G to its
                memory.reclaim, with no cache to give, is EAGAIN and gives back
                at least 64 dentries' worth of that heap, and the sibling's
                kernel is unchanged; a reclaim of one page at the cgroup after
                64 more misses gives back no page and at least one dentry's
                heap (the `reclaim` line of stage 13 that names cached
                dentries). And with kernel objects alone, on every profile, the `core shr` line (user/rehome_cache_check.rs::check_the_shrinker).";
            attribute :>> parent = "H.QUOTA.12";
            attribute :>> unit = ("user::cache::reclaim", "user::cache::shrink",
                "user::cache::install_shrinker", "user::cache::Reclaimed::gave",
                "user::cache::Reclaimed::bytes");
        }
        // The parent is L.object.111's: these are the counts of the cache
        // H.QUOTA.12's reclaim takes, machine-wide rather than per job, and
        // MemAvailable is the room that reclaim makes before anything is
        // killed. No high-level requirement covers /proc's reports as such.
        requirement <'L.object.189'> theWholeCacheIsCounted : ItemLowLevel {
            attribute :>> statement = "totals shall count every live cached
                file's pages, whoever they are charged to: a disk file's, a
                memory filesystem's, of the first those written and not yet
                written back, and those reclaim may take now -- a reclaimable
                object's pages less its dirty ones -- each from the object's own
                count of its pages, for /proc/meminfo's Cached (both kinds),
                Shmem (a memory filesystem's), Dirty and MemAvailable (free and
                what reclaim may take).";
            attribute :>> criterion = "A file written on a writable mount and
                synced is in Cached and in MemAvailable; a page of it written
                again and not synced is in Dirty and not in MemAvailable; a
                tmpfs file's pages are in Cached and Shmem (the `reclaim` line of
                test-btrfs). And with kernel objects alone, on every profile, the `core pc` line (user/rehome_cache_check.rs::check_totals).";
            attribute :>> parent = "H.QUOTA.12";
            attribute :>> unit = ("user::cache::totals", "user::cache::totals_except",
                "user::cache::Share::settle", "user::vmo::Vmo::drop",
                "user::vmo::Vmo::dirty_changed",
                "user::cache::Totals::cached", "user::cache::Totals::available");
        }
        // The write's reclaim and retry (at most eight reclaims, then
        // ENOSPC) are fs/pages.rs's write_reclaiming, load, whose evidence
        // is the stage 12 check write_reclaims_at_max and its control K3
        // (ledger 2026-10-15) and, at the machine's floor with three writers
        // and two readers, test-btrfs-pressure (docs/BTRFS-PRESSURE.md: a
        // machine-wide reclaim asks for the watermark's shortfall besides a
        // run, since 2026-10-17); a fill's (allocate_reclaiming, the same
        // bound, then ENOMEM) is load too, its evidence the stage 12 check
        // fill_reclaims_until_room and its control (ledger line 1637). This
        // states what the core does for it. That the commit and the copy are
        // made under one hold of the pages lock is verified by inspection
        // (the consultant's code review, reviews.md line 1154), not by a
        // check: no boot can show a frame given back mid-copy.
        requirement <'L.object.190'> aWriteIsCopiedUnderThePagesLock : ItemLowLevel {
            attribute :>> statement = "commit_and_write shall commit the page,
                zeroed, if the object lacks it, and copy the bytes at the offset
                into it under one hold of the object's pages lock, writing a
                frame another holder shares in place; with no frame or no room
                to record it, it shall answer OutOfMemory and leave the object as
                it was, so that its caller may reclaim and try again. zero_from
                shall zero a page from the offset to its end under the same lock,
                and leave a page the object lacks absent.";
            attribute :>> criterion = "A 16-page write on a writable btrfs mount,
                in a job at its memory.max holding 32 pages of clean cache of that
                mount, succeeds after its commit was refused and reclaim gave
                pages back, and both files read back as written (the `reclaim`
                line of test-btrfs); a tmpfs file written across pages, cut into
                its second page and grown again reads back its head and zeros
                after the cut (stage 8's tmpfs check). And with kernel objects alone, on every profile, the `core mem` line (user/rehome_check.rs::check_commit_and_write).";
            attribute :>> parent = "H.QUOTA.12";
            attribute :>> unit = ("user::vmo::Vmo::commit_and_write", "user::vmo::Vmo::zero_from");
        }
        // Parents: H.QUOTA.12 for a reclaim inside a job at its limit, whose
        // room must be had before a kill without taking the same pages back
        // again and again; H.QUOTA.13 for the machine at its watermark,
        // where program frames are refused and the reclaim anywhere is what
        // lets them go on.
        requirement <'L.object.191'> reclaimGoesRound : ItemLowLevel {
            attribute :>> statement = "reclaim shall begin where the last reclaim
                stopped, the object and the page, and go once round the live
                cached objects from there in each pass, so that a page is not
                taken again before the pages after it have been looked at.";
            attribute :>> criterion = "A cgroup at its memory.max of 144 pages,
                reading a 128-page stream in 16 steps of 8 pages and an 8-page
                file again after each, with a 128-page file beside it read once,
                has the 8-page file taken back no more than 16 pages (the
                `reclaim` line of stage 13 that names memory.max). And with kernel objects alone, on every profile, the `core pc` line (user/rehome_cache_check.rs::check_a_reclaim_goes_round).";
            attribute :>> parent = ("H.QUOTA.12", "H.QUOTA.13");
            attribute :>> unit = ("user::cache::reclaim", "user::cache::reclaim_pages",
                "user::cache::take_from",
                "user::cache::hand_in", "user::cache::set_hand", "user::cache::object_at",
                "user::cache::Walk::begin", "user::cache::Walk::drop",
                "user::cache::List::close_up");
        }
    }

    package SpeculationDomains {
        doc /* docs/OPAQUE-KERNEL.md §9.2-§9.3a: a job marked at its creation,
             * whose born members' switches skip the predictor invalidation.
             * The customer's decision of 2026-10-01 (docs/BACKLOG.md). */

        requirement <'L.object.113'> barrierSkippedOnlyInsideOneDomain : ItemLowLevel {
            attribute :>> statement = "entered_space shall skip the predictor
                invalidation at a switch of address space only when the outgoing
                space's domain, read as it leaves, and the incoming space's are the
                same and not zero, and shall otherwise decide the barrier as it did
                before; forget_root shall clear a processor's last root where it
                names the root being forgotten, and shall leave its last domain
                as it is (F-64).";
            attribute :>> criterion = "Two members of one marked job switched both
                ways on one processor decide 0 barriers; a member and a process of
                no domain, and members of two marked jobs, decide 2; a switch inside
                the domain issues no invalidation; and a space installed again
                after its root was forgotten decides 1 (the `domain` line, cases 1,
                2 and 10).";
            attribute :>> parent = "H.TRAP.17";
            attribute :>> unit = ("arch::speculation::entered_space",
                "arch::speculation::same_domain", "arch::speculation::left_space",
                "arch::speculation::entering_space", "arch::speculation::forget_root",
                "user::space::AddressSpace::install",
                "user::space::AddressSpace::uninstall");
        }
        requirement <'L.object.114'> markedOnlyAtCreationUnderManage : ItemLowLevel {
            attribute :>> statement = "job_create shall make a job a speculation
                domain only with JOB_SPECULATION_DOMAIN, only under MANAGE on the
                parent, and only as it makes the job; it shall refuse any other
                option bit with INVALID_ARGS, write a DOMAIN audit record for each
                job it marks and none for a refusal, and make every other job,
                a child of a marked one included, in no domain.";
            attribute :>> criterion = "job_create with the option and a parent
                handle without MANAGE answers ACCESS_DENIED, with an unknown bit
                INVALID_ARGS, and neither adds a DOMAIN record; with MANAGE it adds
                one, naming the new job, its parent and its domain (the `domain`
                line, case 4).";
            attribute :>> parent = ("H.TRAP.17", "H.OBJ.8");
            attribute :>> unit = ("syscall::native::job_create",
                "object::job::Job::new_child_domain", "object::job::Job::new_child_in",
                "object::job::Job::domain");
        }
        requirement <'L.object.115'> membershipByBirth : ItemLowLevel {
            attribute :>> statement = "A process shall be in a speculation domain
                only if it was made in the marked job, by process_create or by a
                fork of a member in the same job; its address space shall carry the
                domain, and a space a process of another domain comes to share
                shall be in no domain from then on.";
            attribute :>> criterion = "A process made in a marked job reports the
                job's domain, and a member whose space a process of no domain shares
                decides the barrier both ways with another member (the `domain`
                line, case 6); a marked job inside a marked job is a domain of its
                own (case 7); a child job of a marked job is in no domain, a member's
                fork is a member, and a process moved into a marked job, its fork, and
                a process that left before its birth are not (cases 9 and 10).";
            attribute :>> parent = "H.TRAP.17";
            attribute :>> unit = ("object::process::Process::new",
                "object::process::Process::move_charged",
                "user::space::AddressSpace::claim_domain",
                "user::space::AddressSpace::set_birth_domain",
                "object::process::Process::speculation_domain",
                "user::space::AddressSpace::domain");
        }
        requirement <'L.object.116'> leavingIsForGood : ItemLowLevel {
            attribute :>> statement = "A member shall leave its speculation domain
                for good, and its address space with it, when it moves between jobs,
                and when it stops being dumpable: a set-id execve, a change of
                credentials, or PR_SET_DUMPABLE; and every processor whose last space
                was in the domain shall issue the barrier before the leave returns.
                In hardened builds the leave shall find them two ways, and wait for
                a grace period: a scan that asks each processor whose last domain is
                the leaver's, and a local check by which each processor, answering
                the leave's grace period with interrupts masked, compares its own
                last domain with the domains being left and issues the barrier
                itself on a match. A build with the mitigations off has no barrier,
                and its leave waits for no grace period. Each domain being left
                shall be published in a slot of its own in a set, sequentially
                consistent and before the scan and before the grace period's
                generation is advanced, and the answering processor shall read the generation
                before the set, so that one that records the domain after the scan
                has passed it is still found (F-60).";
            attribute :>> criterion = "A member moved out of its job, one whose
                credentials changed and one made not dumpable each decide the
                barrier both ways with a member left in the domain (the `domain`
                line, cases 3 and 5); a member that leaves makes this processor and one
                running a thread in its space each decide the barrier before the
                leave returns (case 8); and a processor made, by stage 9's hook
                between the scan and the grace period, to record the domain after
                the scan has passed it decides the barrier before the leave returns
                (case 11), which the local check removed fails; and a processor
                made, by stage 9's hook in forget_root after the clear of its last
                root, to switch into a member's space decides the barrier when that
                member leaves there (case 12), which forget_root's old store of zero
                to the processor's last domain fails (F-64).";
            attribute :>> parent = "H.TRAP.17";
            attribute :>> unit = ("object::process::Process::leave_speculation_domain",
                "object::process::Process::leave_speculation_domain_unstarted",
                "arch::speculation::leaving_domain", "arch::speculation::serve_wanted_barrier",
                "arch::speculation::answer_leaving", "smp::answer_grace_periods",
                "user::space::AddressSpace::leave_domain");
        }
    }

    package DeviceConfiguration {
        doc /* A published PCI node's configuration space, written by the kernel
             * and, through device_config_write, by its driver: one lock per
             * node, as a type (docs/NVIDIA.md section 12.1). */

        requirement <'L.object.117'> oneConfigurationLockPerNode : ItemLowLevel {
            attribute :>> statement = "Every write to a published node's PCI
                configuration space, by the kernel or by a driver, shall be made
                holding the node's one configuration lock, through the one type
                that holds it; enumeration's writers run at stage 10, before any
                node is published.";
            attribute :>> criterion = "A ConfigWrites is made only by taking the
                lock, MappedConfig has no write, and bus mastering, an MSI mint and
                mask, MSI-X's enable and a driver's write go through ConfigWrites.
                Bus mastering switched on and off on one processor while another
                makes a driver's configuration writes to the same function, 1,000
                rounds, reads back as dma_on says every time (the second config
                line).";
            attribute :>> parent = ("H.DMA.5", "H.IRQ.2");
            attribute :>> unit = ("device::DeviceNode::config_writes",
                "device::DeviceNode::config_writes_mapped", "device::DeviceNode::set_bus_master",
                "device::DeviceNode::config_mapping", "device::ConfigWrites::write",
                "device::ConfigWrites::inside", "device::MsiFunction::mint",
                "device::MsiFunction::set_masked", "device::MsixTable::open");
        }
    }

    package ChannelWriteRead {
        doc /* docs/OPAQUE-KERNEL.md §9.4, items 3 and 4: channel_write_read
             * (0x1013), the inbox's slot it writes into, its answer in
             * registers, and the wait it trusts. Checked through each
             * architecture's own entry by object::write_read_check, the
             * `wrread` line. */

        requirement <'L.object.128'> aSmallMessageIsHeldInTheSlot : ItemLowLevel {
            attribute :>> statement = "Endpoint::write_small shall refuse a message
                as Endpoint::write does -- the peer closed, more bytes than three
                words, the queue full -- and shall otherwise hold a message of at
                most three words without handles in the peer's slot only while
                nothing waits there and the inbox's spare has room for it or can be
                given it, queueing it behind what does, so that the slot always
                holds the oldest message and a buffer for it.";
            attribute :>> criterion = "A small message written behind a queued one
                is read after it, and a send to a closed peer, one past three words
                and one on a handle without WRITE send nothing (the `wrread` line).";
            attribute :>> parent = "H.OBJ.10";
            attribute :>> unit = ("object::channel::Endpoint::write_small",
                "object::channel::Inbox::put_small", "object::channel::Inbox::is_empty",
                "object::channel::Small::of", "object::channel::Inbox::drain");
        }
        requirement <'L.object.129'> theSlotIsEveryReadersHead : ItemLowLevel {
            attribute :>> statement = "Endpoint::read shall take the message held
                in the slot before any queued, as a message without handles in the
                inbox's spare, never failing for memory, leave it with its size
                reported when the caller has too little room, and Endpoint::unread
                shall put a message back ahead of one the slot has taken since, so
                that every reader sees the messages in the order written.";
            attribute :>> criterion = "A message held in the slot is read before
                one queued after it; a read with room for 2 bytes of a 5-byte slot
                message is refused with its size and the next read returns it whole;
                a message taken from the slot and put back after the slot took
                another is read first, then the other (the `wrread` line).";
            attribute :>> parent = "H.OBJ.7";
            attribute :>> unit = ("object::channel::Inbox::pop_fitting",
                "object::channel::Inbox::unpop", "object::channel::Inbox::head_needs_topology",
                "object::channel::Inbox::take_spare");
        }
        requirement <'L.object.130'> aSmallReadIsBytesThenZeros : ItemLowLevel {
            attribute :>> statement = "Endpoint::read_small shall take the oldest
                message only if it carries no handles and at most three words, and
                give its bytes followed by zeros to the width of three words; it
                shall leave any other message queued and report its size.";
            attribute :>> criterion = "A 5-byte message held in the slot and a
                7-byte message queued each come back from channel_write_read as
                their bytes then zeros, and a 40-byte message is refused by a small
                read and then read whole (the `wrread` line).";
            attribute :>> parent = "H.OBJ.7";
            attribute :>> unit = ("object::channel::Endpoint::read_small",
                "object::channel::Inbox::pop_small", "object::channel::Small::of");
        }
        requirement <'L.object.131'> theAnswerInRegisters : ItemLowLevel {
            attribute :>> statement = "channel_write_read shall send its count bytes
                from its third to fifth argument registers, then answer the next
                message on the same end with its size in the return register and its
                words in the second to fourth argument registers, zero past its
                bytes; a call that fails shall answer its status in the return
                register alone and leave the second to fourth argument registers as
                the program set them, on each architecture's entry.";
            attribute :>> criterion = "Through the entry, a call that sends 3 bytes
                and finds a 4-byte answer waiting answers 4 and its words, and the
                peer reads the 3 bytes then zeros; a closed handle, a count past
                three words, a send without WRITE, a message too big for registers,
                and a send and a receive on a closed peer each answer their status
                with registers 2 to 4 as sent, 6 of 6 (the `wrread` line).";
            attribute :>> parent = ("H.TRAP.10", "H.OBJ.2");
            attribute :>> unit = ("syscall::native::channel_write_read",
                "syscall::native::dispatch_write_read", "syscall::native::send_words",
                "syscall::native::receive_words", "syscall::native::read_refusal",
                "syscall::native_call", "arch::x86_64::syscall::ferrix_syscall_entry",
                "arch::aarch64::trap::system_call", "arch::armv7a::trap::system_call",
                "arch::armv7a::trap::store_words");
        }
        requirement <'L.object.132'> aTrustingWaitIsWokenByWhatEndsIt : ItemLowLevel {
            attribute :>> statement = "channel_write_read's wait shall file no
                recheck while it is listed on its end's queue, and shall end on each
                of what it waits for: a message arriving on the end, the peer's
                close, and its process's end or another thread's execve, each of
                which wakes it; it shall then answer the message, PEER_CLOSED, or
                EINTR. The message and the close shall be read from the end's state
                word and the end or execve from the task's END bit, each ordered
                against the task's blocked state by a SeqCst fence on each side
                (L.object.141, L.sched.40).";
            attribute :>> criterion = "A thread blocked in channel_write_read and
                listed on its end's queue is woken within 10 s by a message, which it
                answers, by its peer's close, which it answers PEER_CLOSED, and by
                its process's kill, after which its thread ends (the `wrread`
                line).";
            attribute :>> parent = "H.OBJ.11";
            attribute :>> unit = ("object::channel::Endpoint::readable_or_closed",
                "sched::wait::WaitQueue::wait_trusting", "sched::wait::WaitQueue::wait_sliced",
                "object::channel::Endpoint::drop");
        }
        requirement <'L.object.247'> aPortWaitTrustsItsWakes : ItemLowLevel {
            attribute :>> statement = "port_wait's wait shall file no recheck
                while it is listed on its port's queue, and shall end on each of
                what it waits for: a packet queued on the port by queue_user,
                queue_signal, queue_interrupt, put_back or an interrupt's fire,
                each of which wakes the queue after its push; its process's end
                or another thread's execve, read from the task's END bit under
                the SeqCst fence pair with wake_posted (L.sched.40), answering
                EINTR; and its deadline, answering TIMED_OUT. A task there was
                no memory to list shall recheck every 5 ms whatever its
                deadline.";
            attribute :>> criterion = "A thread blocked in port_wait with a
                two-minute deadline is woken within 10 s by a packet its
                registration queues twenty milliseconds later (object::check); a thread blocked in
                port_wait with no deadline and listed on its port's queue is
                ended by its process's kill within 10 s, and its thread ends (the
                `wrread` line).";
            attribute :>> parent = "H.OBJ.11";
            attribute :>> unit = ("sched::wait::WaitQueue::wait_trusting_until",
                "sched::wait::WaitQueue::wait_sliced", "syscall::native::port_wait",
                "object::port::Port::queue_user", "object::port::Port::queue_signal",
                "object::port::Port::queue_interrupt", "object::port::Port::put_back",
                "object::interrupt::Line::fire");
        }
        requirement <'L.object.248'> aSealedJobRefusesMoves : ItemLowLevel {
            attribute :>> statement = "Process::move_to shall refuse to move a
                started process out of a sealed job or into one, leaving it in
                its job; a cgroup.procs write so refused shall answer EPERM
                whoever writes, a privileged writer in the initial cgroup
                namespace included.";
            attribute :>> criterion = "Stage 13's cgroupfs check: root's writes
                moving a process out of a sealed job, between two jobs of its
                tree and into it answer EPERM, 3 of 3, and each process is still
                in its job.";
            attribute :>> parent = "H.OBJ.22";
            attribute :>> unit = ("object::process::Process::move_charged",
                "object::job::Job::seal_refuses");
        }
        requirement <'L.object.249'> aSealedJobsStartsStayInside : ItemLowLevel {
            attribute :>> statement = "Job::may_start_in shall allow a member of a
                sealed job to start a process only in that job or a job beneath
                it, and shall allow a start in a sealed job from outside it only
                as native process_create's.";
            attribute :>> criterion = "Stage 13's cgroupfs check: may_start_in
                refuses a sealed member's start outside its tree and an outside
                start into a sealed job, and allows a sealed member's start into
                its own inner job. And with kernel objects alone, on every profile, the `core obj` line (object/rehome_check.rs::check_may_start_in).";
            attribute :>> parent = "H.OBJ.22";
            attribute :>> unit = ("object::job::Job::may_start_in");
        }
        requirement <'L.object.250'> sealedAsMade : ItemLowLevel {
            attribute :>> statement = "A job shall be sealed exactly when it was
                made with JOB_SEALED or inside a sealed job, fixed before it is
                listed in its parent, and never unsealed; job_create shall
                refuse any option bit but JOB_SPECULATION_DOMAIN and JOB_SEALED
                with INVALID_ARGS, before anything is made.";
            attribute :>> criterion = "Stage 13's cgroupfs check: a job made with
                JOB_SEALED, one made inside it by job_create without the bit and
                one made inside it by mkdir read as sealed, the cgroup they were
                made in does not, and an unknown option bit is INVALID_ARGS. And with kernel objects alone, on every profile, the `item` line (syscall/rehome_check.rs::check_job_create).";
            attribute :>> parent = "H.OBJ.22";
            attribute :>> unit = ("object::job::Job::bare_child",
                "object::job::Job::new_child_as", "object::job::Job::new_named_child_as",
                "syscall::native::job_create");
        }
        requirement <'L.object.251'> aSealedMemberCreatesInside : ItemLowLevel {
            attribute :>> statement = "process_create by a process whose job is
                sealed shall refuse a job outside that job's tree with
                ACCESS_DENIED and make nothing.";
            attribute :>> criterion = "Stage 13's cgroupfs check: a check process
                in a sealed job is refused process_create into an outside job with
                ACCESS_DENIED, and passes that refusal for its own inner job.";
            attribute :>> parent = "H.OBJ.22";
            attribute :>> unit = ("syscall::native::process_create");
        }
        requirement <'L.object.252'> theMemoryScrubToken : ItemLowLevel {
            attribute :>> statement = "The kernel shall make one memory scrub token and give it to
                pid 1 after the processor service token, with MANAGE,
                DUPLICATE and TRANSFER, once.";
            attribute :>> criterion = "The native boot check pins MEMORY_SCRUB_RIGHTS to MANAGE,
                DUPLICATE and TRANSFER; test-scrub: memscrub scrubs through
                the copy init granted it.";
            attribute :>> parent = "H.FAIL.9";
            attribute :>> unit = ("init::give_memory_scrub");
        }
        requirement <'L.object.259'> aPoisonedCachedPageIsDroppedOnlyClean : ItemLowLevel {
            attribute :>> statement = "cache::drop_poisoned shall retire the frame before it
                takes anything and take nothing unless the retirement answered
                Claimed, Marked or Already; shall find the frame's page by a walk
                of the cache list under the walker count, scanning each object's
                page map at most 32 entries a hold of its pages lock; shall take
                the page only through reclaim_clean's test, with the frame checked
                again to be the page's in the take's hold of the pages lock, out of
                the object and every space that maps it; and shall answer Clean,
                NotClean (also for a clean page the source holds still at that
                moment for a write, a truncation, a writeback or a reclaim of its
                file), NotRetired or NotCache.";
            attribute :>> criterion = "Stage 12's poison check: a clean mapped page dropped, its
                frame retired, gone from the object and the mapping, read again
                with the disk's bytes; a dirty and a held page NotClean and kept;
                an unheld frame NotCache; a frame not retirable NotRetired; a page
                asked for with another frame NotCache and kept. Controls: the
                clean test, the retirement's answer and the frame check removed. And with kernel objects alone, on every profile, the `core pc` line (user/rehome_cache_check.rs::check_a_poisoned_page_is_dropped).";
            attribute :>> parent = "H.FAIL.11";
            attribute :>> unit = ("user::cache::drop_poisoned", "user::cache::drop_poisoned_at", "user::cache::retire", "user::cache::take", "user::cache::say", "user::vmo::Vmo::index_of", "user::vmo::Vmo::take_poisoned");
        }
        requirement <'L.object.260'> aCacheReadAnswersItsPoison : ItemLowLevel {
            attribute :>> statement = "Vmo::read_present shall copy through arch::copy_mc,
                answer Poisoned(frame) for a copy a machine check stopped after
                checking the page against the frame it read (stopping as FX-9005
                on another), and write no task record.";
            attribute :>> criterion = "Stage 12's poison check: a read whose copy is answered as
                poisoned retires and drops the page; test-mce-pagecache's read
                mode. Control: Poisoned turned into EIO. And with kernel objects alone, on every profile, the `core pc` line (user/rehome_cache_check.rs::check_read_present_answers_poison).";
            attribute :>> parent = "H.FAIL.11";
            attribute :>> unit = ("user::vmo::Vmo::read_present");
        }
        requirement <'L.object.261'> aPoisonedReadIsRefilledOrFails : ItemLowLevel {
            attribute :>> statement = "cache::poisoned_read, which a read whose copy answered
                Poisoned calls with no lock held, shall drop the page through
                drop_poisoned_at and answer go round the fill loop again only
                after Clean (or a page no longer holding the frame), and fail EIO
                after NotClean or NotRetired.";
            attribute :>> criterion = "Stage 12's poison check: a clean page's poisoned read
                refilled and answered with the disk's bytes; a dirty page's fails;
                test-mce-pagecache's read and dirty modes. Control: the refill on
                Clean removed. And with kernel objects alone, on every profile, the `core pc` line (user/rehome_cache_check.rs::check_a_poisoned_read).";
            attribute :>> parent = "H.FAIL.11";
            attribute :>> unit = ("user::cache::poisoned_read");
        }
        requirement <'L.object.262'> theQuarantineLeavesARetiredFrameUnread : ItemLowLevel {
            doc /* docs/MACHINE-CHECK-DRIVER.md §2.1 (customer, 2026-10-30, item 5; consultant NOT YET ledger 5435, OK IF ledger 5444). */
            attribute :>> statement = "The pin quarantine shall not read a retired frame --
                neither at a dead driver's pin's close nor at its release -- and
                shall count each frame left unread and say the count in the
                release line; every other frame shall be read and compared as
                before.";
            attribute :>> criterion = "The pin check's check_retired_unread: a frame the check
                names retired left unread at the close and the release (the count
                up by two, the release's retired 1), one not named read at both;
                test-mce-driver's Own under KVM and TCG: the release after the
                restart says 1 retired, not read. Negative controls: the skip
                removed at the close, and at the release, each fires the check.";
            attribute :>> parent = "H.FAIL.8";
            attribute :>> unit = ("object::pin::left_unread",
                "mm::frame_retired",
                "object::pin::retired_for_check",
                "object::pin::quarantine_release",
                "object::pin::release");
        }
        requirement <'L.object.140'> anEndsWordIsItsInbox : ItemLowLevel {
            attribute :>> statement = "Under a channel end's inbox lock, its state
                word's NONEMPTY shall be set exactly when the inbox holds a message,
                after every operation that changes that -- a write, a small write, a
                read, a small read, a put-back and the close's drain -- and its
                PEER_CLOSED shall be set once the peer has closed, after the peer's
                closed and before the end's waiters are woken.";
            attribute :>> criterion = "4096 writes, small writes, reads, small reads
                and put-backs in a pseudo-random order on one pair leave each end's
                word equal to its inbox after every one, each operation having
                crossed the empty boundary once first, and a close is marked in the
                survivor's (the `chword` line); with the put-back's update removed
                the check fails after a put-back into an empty inbox.";
            attribute :>> parent = "H.OBJ.11";
            attribute :>> unit = ("object::channel::Half::note",
                "object::channel::Half::note_peer_closed", "object::channel::Half::word",
                "object::channel::Endpoint::read", "object::channel::Endpoint::read_small",
                "object::channel::Endpoint::write", "object::channel::Endpoint::write_small",
                "object::channel::Endpoint::unread", "object::channel::Endpoint::take_unread");
        }
        requirement <'L.object.141'> aWakerFencesTheWordBeforeItsWake : ItemLowLevel {
            attribute :>> statement = "channel_write_read's wait shall read readiness
                with one load of its end's state word and one of the caller's END
                bit, without the inbox lock or the personality; and a writer, a
                put-back and a closer shall make a SeqCst fence after the word's
                store and before their wake reads a waiter's state, paired with the
                wait's fence after it stores BLOCKED, so that a waiter listed and
                not yet blocked either is found blocked or reads the word.";
            attribute :>> criterion = "The `wrread` line's message and close cases;
                with the close's mark removed, the close case's waiter stays blocked
                and the check fails by name. The loom model of a
                waiter listed and not yet blocked against a writer, a closer, both,
                and an end finds no lost wake, and its two controls, the writer
                without its fence and the closer marking after its wake, each find
                one (`cargo xtask loom`, src/tests/loom).";
            attribute :>> parent = "H.OBJ.11";
            attribute :>> unit = ("object::channel::Endpoint::readable_or_closed",
                "syscall::native::receive_words", "sched::work::own_end");
        }
    }

    package FastPath {
        doc /* src/kernel/src/object/channel.rs and src/kernel/src/syscall/native.rs:
             * channel_write_read's fast path, its park and its continuation
             * (docs/OPAQUE-KERNEL.md §9.7, parts 2 and 3). x86-64 only. */

        requirement <'L.object.164'> aParkIsSetBesideAnEmptyInbox : ItemLowLevel {
            attribute :>> statement = "A park record shall be set only while its
                side's inbox is empty, nothing else is parked there and the peer has
                not closed, with its task set blocked in the same hold of the inbox
                lock; the receive half then makes a SeqCst fence and looks at END
                before it blocks.";
            attribute :>> criterion = "Case 4's two readers are both answered (the
                `fastcase` line); the loom model park.rs and its controls.";
            attribute :>> parent = "H.OBJ.18";
            attribute :>> unit = ("object::channel::Endpoint::park",
                "syscall::native::park_for_reply", "sched::direct::block_parked",
                "sched::direct::set_blocked");
        }
        requirement <'L.object.165'> aGeneralWriterWakesThePark : ItemLowLevel {
            attribute :>> statement = "A write, write_small, unread or close that
                changes an inbox shall take its park record under the inbox lock and
                wake the parked task after letting the lock go, counting the wait as
                ended by a wake.";
            attribute :>> criterion = "write_read_check's waits and the continuation's
                message and close cases end within the bound with the fast path on;
                with the take left out the loom control strands a reader.";
            attribute :>> parent = "H.OBJ.18";
            attribute :>> unit = ("object::channel::Inbox::take_parked",
                "object::channel::wake_parked", "sched::wait::WaitQueue::note_ended_by_a_wake");
        }
        requirement <'L.object.166'> theSendHalfDeclinesOrCommits : ItemLowLevel {
            attribute :>> statement = "send_direct shall take the two halves' inbox
                locks only if free, the first side's before the second's, held under
                the entry's interrupt mask and counted as locks on the preemption word
                that A3 checks at the switch, decline
                unless the caller's inbox is empty (T6), nothing is parked on its side
                (T7), its peer is open (T8), a reader is parked on the peer's side
                (T9) and the peer's side has no observers and no waiters (T10), stop
                the machine with FX-0531 for a record beside a message or on a
                closed end (A2), and otherwise fill the reader's reply cell, park
                the caller and hand the processor over.";
            attribute :>> criterion = "ipc-equiv's cases 3, 5, 8 and 12, and stage 9's
                case 4, reach T6 to T10 with the fast path on and get the general
                path's results; each test's control fails its case.";
            attribute :>> parent = "H.OBJ.18";
            attribute :>> unit = ("object::channel::Endpoint::send_direct",
                "object::channel::sendable");
        }
        requirement <'L.object.167'> theReplyIsZeroPastItsCount : ItemLowLevel {
            attribute :>> statement = "The words a commit hands over shall be the
                count's bytes of the sent words, the bytes past the count zero.";
            attribute :>> criterion = "ipc-equiv's case 1 with the fast path on, and
                stage 9's reply-words case, which holds the commit's words to the
                general write then read for every count (the `fastcase` line); with
                the mask past the count left out its control fails it.";
            attribute :>> parent = "H.OBJ.18";
            attribute :>> unit = ("syscall::native::reply_words", "syscall::native::words_of",
                "syscall::native::sent_bytes");
        }
        requirement <'L.object.168'> theContinuationIsTheGeneralPath : ItemLowLevel {
            attribute :>> statement = "A caller the fast path parked and woken without
                a reply shall open interrupts, stop with FX-0533 if it may not block,
                leave its record, answer EINTR if END is posted or carry on as
                receive_words does, write the call's audit record as
                dispatch_write_read does, let go of its endpoint reference before it
                masks interrupts again, and run regroup_current and call_left.";
            attribute :>> criterion = "The continuation's cases by a message, its
                peer's close and its kill answer the message, PEER_CLOSED and EINTR
                (the `fastcase` line); case 16's continuation variant closes its end
                with interrupts open (F-65).";
            attribute :>> parent = "H.OBJ.18";
            attribute :>> unit = ("syscall::native::continue_general",
                "object::channel::Endpoint::unpark");
        }
        requirement <'L.object.169'> theFastPathLooksAsTheGeneralPathDoes : ItemLowLevel {
            attribute :>> statement = "fast_write_read shall decline, having changed
                nothing but its counts, unless the filter would let the
                call through unlooked at (T2), it sends at most 24 bytes (T3), and the
                handle table's lock is free and channel_in finds an endpoint with
                READ and WRITE (T4, T5).";
            attribute :>> criterion = "Stage 9's case 11 is refused with the filter's
                errno with the fast path on, and comes back with IN_CALL down whether
                refused or allowed; ipc-equiv's case 12 answers every
                refusal as the general path does, with its audit records; every
                stage 9 echo's task names, as its cached core process, the one its
                thread's process holds.";
            attribute :>> parent = "H.OBJ.18";
            attribute :>> unit = ("syscall::native::fast_write_read",
                "object::process::Process::try_with_handles_masked",
                "sched::task::Task::core_process", "trap::filter_quiet",
                "trap::set_quiet_syscall_filter");
        }
        requirement <'L.object.170'> theWayOutsAreShared : ItemLowLevel {
            attribute :>> statement = "channel_write_read's answer shall go into the
                program's registers through write_read_outcome on the general path,
                the frame tail and the continuation alike.";
            attribute :>> criterion = "ipc-equiv's transcripts are the same on both
                boots.";
            attribute :>> parent = "H.OBJ.18";
            attribute :>> unit = "syscall::write_read_outcome";
        }
        requirement <'L.object.179'> theFastPathLetsGoOfItsEndUnmasked : ItemLowLevel {
            attribute :>> statement = "fast_write_read shall let go of its reference
                to the caller's endpoint only with interrupts open, on the frame
                tail's return, the general continuation and a decline after the
                lookup alike, and a channel end closed with interrupts masked shall
                stop the machine with FX-0535 (F-65).";
            attribute :>> criterion = "Stage 9's case 16: a caller parked by the fast
                path whose handle another thread closes, resumed by the frame tail
                and by the continuation, answers 'r' and 'm', its sink sees
                PEER_CLOSED, and the boot does not stop with FX-0535; the frame
                tail's variant counts only when the sink's reply was handed over
                directly too. The decline's release is argued (it goes through the
                same release_unmasked), not driven.";
            attribute :>> parent = "H.OBJ.18";
            attribute :>> unit = ("syscall::native::release_unmasked",
                "object::channel::Endpoint::drop");
        }
        requirement <'L.object.180'> cpuTimeIsKeptBackOnce : ItemLowLevel {
            attribute :>> statement = "A run queue's charge of processor time to a
                job shall be kept back in the queue's Pending record, holding the
                job's slot, and moved into the slots of the job and every job above
                it and into the machine's exactly once: when the queue charges
                another job, when it switches to a task of another job or to its
                idle task, when its running task leaves its job, and when every
                processor's running task is charged up to now (sched::charge_running:
                a read of cpu.stat, or of another thread's processor time through
                /proc's stat, CLOCK_PROCESS_CPUTIME_ID, times or getrusage's
                RUSAGE_SELF); after the move it shall hold no slot it no longer
                charges.";
            attribute :>> criterion = "On records of its own, two charges to a
                child job stay pending and hold its slot; a charge to the parent
                moves the first into both slots and the machine once; flushes to
                no job settle child 1000 20, parent 1000 320, machine 1000 320,
                leave nothing pending and give back both holds. A running task
                moved into a job and charged has that time in the job's cpu.stat
                once charge_running has run, with nothing switched; moved back,
                it leaves its queue keeping nothing for that job, and the job
                gone, its slot is free.";
            attribute :>> parent = "H.QUOTA.10";
            attribute :>> unit = ("object::quota::add_cpu_time",
                "object::quota::Pending::charge", "object::quota::Pending::flush",
                "object::quota::switched", "object::quota::leaving",
                "object::quota::settle");
        }
        requirement <'L.object.254'> pinBlocksOptionWord : ItemLowLevel {
            attribute :>> statement = "vmo_pin shall refuse with INVALID_ARGS, before
                any frame is taken, an option word with an order in bits 8-11 and
                no PIN_BLOCKS, PIN_BLOCKS with order 0 or an order above the frame
                allocator's largest, PIN_BLOCKS with PIN_CONTIGUOUS, and any bit
                above bit 11 or bit 4 to 7.";
            attribute :>> criterion = "Stage 10's PIN_BLOCKS check: each of the four
                words on a PCI function's node is INVALID_ARGS and the VMO commits
                no page; the pin refusals check's unknown option 16 is
                INVALID_ARGS.";
            attribute :>> parent = "H.DMA.3";
            attribute :>> unit = ("syscall::native::vmo_pin", "syscall::native::pin_block_order");
        }
        requirement <'L.object.255'> pinBlocksAreNaturallyAligned : ItemLowLevel {
            attribute :>> statement = "With PIN_BLOCKS of order k, vmo_pin shall
                commit each absent page of its range only as part of a block of
                2^o pages, o at most k, that starts at a VMO page and at a frame
                that are both multiples of 2^o, lies inside the range and held no
                committed page when it was probed; a page committed before the
                call shall keep its frame.";
            attribute :>> criterion = "Stage 10's PIN_BLOCKS check: over 1024 pages
                with page 3 committed first, page 3 keeps its frame, pages 0-1, 2,
                4-7, 8-15 up to 256-511 and 512-1023 are each one run of frames
                from a multiple of its length, and pages 0-1023 are not one run
                from a multiple of 1024.";
            attribute :>> parent = "H.DMA.3";
            attribute :>> unit = ("user::vmo::Vmo::commit_blocks", "syscall::native::vmo_pin",
                "syscall::native::commit_blocks_for_pin");
        }
        requirement <'L.object.256'> pinBlocksFallBack : ItemLowLevel {
            attribute :>> statement = "Vmo::commit_blocks shall, where the frame
                allocator refuses a block, try the next lower order and never again
                an order above one refused in the same call; end at a refused
                single frame; take a page committed between a block's probe and
                its commit as a reason for a lower order, never a higher one, and
                leave that page's frame as it is; and ask Vmo::commit_run at most
                the range's pages plus the largest order plus one times.";
            attribute :>> criterion = "Stage 10's PIN_BLOCKS check: with every
                32-frame region of free memory holding a kept frame, 512 pages
                asked at order 9 are all committed, at least one ask was refused,
                no 32 pages from a multiple of 32 are one run of frames from a
                multiple of 32, and the refusals are at most five more than the
                blocks; with the block hook committing page 100 at the first
                block's commit, page 100 keeps the hook's frame and all 512 are
                committed; in every case the asks stay within the bound.";
            attribute :>> parent = "H.DMA.3";
            attribute :>> unit = ("user::vmo::Vmo::commit_blocks", "user::vmo::Vmo::block_at",
                "user::vmo::run_block_hook");
        }
        requirement <'L.object.257'> pinBlocksBudgetAndFailure : ItemLowLevel {
            attribute :>> statement = "vmo_pin with PIN_BLOCKS shall check the
                device's pin budget before committing any page, refusing a range
                past it with LIMIT_REACHED and nothing committed; and a PIN_BLOCKS
                pin refused after its pre-commit shall leave committed exactly the
                pages the pre-commit committed, each charged to the caller's job,
                where the refusal is the job's memory limit. A pin refused for
                want of memory shall first take back clean file cache, charged to
                the job whose memory limit is full or beneath it or, with no limit
                full, anywhere, and try again while that gave back any, at most
                16 times, before it answers NO_MEMORY.";
            attribute :>> criterion = "Stage 10's PIN_BLOCKS check: a pin of the
                budget plus one page is LIMIT_REACHED with no page committed; a pin
                of 512 pages by a job limited to 256 pages' memory is NO_MEMORY,
                the VMO holds some pages and exactly that many are charged to the
                job, and none once the VMO is gone; a pin of 512 pages by a job
                limited to 1024 pages and filled to its limit with a file's clean
                cache is answered, all 512 pages committed, the file holding fewer
                pages than before.";
            attribute :>> parent = ("H.DMA.3", "H.QUOTA.2");
            attribute :>> unit = ("syscall::native::vmo_pin",
                "syscall::native::commit_blocks_for_pin", "user::vmo::Vmo::commit_blocks",
                "object::oom::reclaim_for");
        }
        requirement <'L.object.258'> pinBlocksLeaveFilesAlone : ItemLowLevel {
            attribute :>> statement = "Vmo::commit_blocks shall commit no page of a
                file's VMO.";
            attribute :>> criterion = "Stage 10's PIN_BLOCKS check: on a VMO over a
                source, commit_blocks asks commit_run never and the VMO holds no
                page.";
            attribute :>> parent = "H.DMA.3";
            attribute :>> unit = ("user::vmo::Vmo::commit_blocks");
        }
    }

    package SenderIdentity {
        doc /* docs/microkernel/K6.md: kernel-attested sender identity on a
             * channel message (MICROKERNEL.md §3 K6), the consultant's OK IF at
             * ledger 2485 and 2524. Checked by object::sender_check, the
             * `sender` line, and fs::exec_check's execve case. */

        requirement <'L.object.197'> everyWriteIsStamped : ItemLowLevel {
            attribute :>> statement = "Every channel write shall stamp its message,
                under the peer's inbox lock, with the Sender its caller names: a
                program's write, by channel_write or channel_write_read, with
                Sender::of its own process, its id and its job at the write; the
                kernel's with Sender::KERNEL, zero and zero. The stamp shall be
                carried unchanged through the queue, the slot, which holds a
                message and its stamp as one, a put-back, and the transfer of either
                end; a Sender shall be made only by Sender::of and Sender::KERNEL.";
            attribute :>> criterion = "Cases 1, 2, 3 and 7 of the `sender` line;
                controls C1 to C4 fire on their cases.";
            attribute :>> parent = "H.OBJ.19";
            attribute :>> unit = ("object::channel::Sender::of",
                "object::channel::Endpoint::write", "object::channel::Endpoint::write_small",
                "object::channel::Inbox::put_small", "object::channel::Inbox::pop_fitting",
                "object::channel::Inbox::unpop");
        }
        requirement <'L.object.198'> aProcessIdIsGivenOnce : ItemLowLevel {
            attribute :>> statement = "A process's id shall be given once, as its
                core process is made, from a counter that only grows and starts at
                one; it shall be held by the process's Exit, kept across execve,
                and never given to another process.";
            attribute :>> criterion = "Case 5 of the `sender` line: plain, forked
                and process_create processes each above every earlier id, and one
                made after another ended not given its id; stage 8's exec check: the
                id after an execve is the id before, and a message written after it
                reads as that id; control C5 fires.";
            attribute :>> parent = "H.OBJ.19";
            attribute :>> unit = ("object::process::next_id", "object::process::Process::id",
                "object::process::Exit::id");
        }
        requirement <'L.object.199'> aReadSaysWhoWrote : ItemLowLevel {
            attribute :>> statement = "channel_read_attested (0x1014) shall answer as
                channel_read and, on success, write a ReadAttested holding the sizes
                and the message's stamp after the bytes and the handles, byte by byte
                with no alignment assumed; on BUFFER_TOO_SMALL it shall write the
                sizes only, and a delivery whose record cannot be written shall put
                the message back with its stamp.";
            attribute :>> criterion = "Cases 1 to 4, 6, 7 and 9 of the `sender`
                line, every record at an address one past an 8-byte boundary; a read
                without READ is ACCESS_DENIED, one too small writes the sizes only,
                one with an unwritable record is FAULT and the message is read again
                whole as its writer's.";
            attribute :>> parent = "H.OBJ.19";
            attribute :>> unit = ("syscall::native::channel_read",
                "syscall::native::record_bytes", "syscall::native::deliver");
        }
        requirement <'L.object.200'> anIdNamesAProcessOrAJob : ItemLowLevel {
            attribute :>> statement = "object_id (0x100A) shall write the id of the
                process or job a handle with any rights names, a process's also after
                it has ended, and refuse any other object WRONG_TYPE, a handle not
                held BAD_HANDLE and an unwritable answer FAULT.";
            attribute :>> criterion = "Cases 1, 4 and 9 of the `sender` line.";
            attribute :>> parent = "H.OBJ.19";
            attribute :>> unit = "syscall::native::object_id";
        }
        requirement <'L.object.201'> theJobIsTheJobAtTheWrite : ItemLowLevel {
            attribute :>> statement = "The job in a program's stamp shall be the job
                its process was in at the write, read without the membership lock
                from a mirror written under it wherever the process's job changes.";
            attribute :>> criterion = "Case 6 of the `sender` line: a process moved
                between two writes stamps each with its job then; control C6 fires.";
            attribute :>> parent = "H.OBJ.19";
            attribute :>> unit = ("object::process::Process::job_id",
                "object::process::Process::move_charged", "object::process::Process::new");
        }
        requirement <'L.object.202'> theRoundTripAnswersNoSender : ItemLowLevel {
            attribute :>> statement = "channel_write_read shall answer no sender on
                either path: its read drops the slot's stamp, and the fast path's
                commit hands its words to the parked reader without one and puts no
                message in an inbox. A server that answers and waits through it
                receives its next request without identity, and reads with
                channel_read_attested where it decides by sender.";
            attribute :>> criterion = "Case 8 of the `sender` line: the writer's
                empty answer is zero and three zero words; ipc-equiv's transcripts
                agree with the fast path on and off.";
            attribute :>> parent = "H.OBJ.19";
            attribute :>> unit = ("object::channel::Inbox::pop_small",
                "object::channel::Endpoint::send_direct");
        }
    }

    package Timers {
        doc /* src/kernel/src/object/timer.rs, its arms on the sleeper sets of
            src/kernel/src/sched/queue.rs, and the calls in syscall/native.rs
            (docs/microkernel/K10.md). */

        requirement <'L.object.213'> aTimerIsChargedToItsJob : ItemLowLevel {
            attribute :>> statement = "timer_create shall make a disarmed timer on
                the monotonic or the boot clock, refusing any other clock or an
                option with INVALID_ARGS; it shall charge the caller's job one
                object and the timer's heap as kernel memory before the handle
                exists, refuse NO_MEMORY with nothing made at either limit, and
                the timer's drop shall take both back.";
            attribute :>> criterion = "A timer made in a job raises its objects by
                1 and its kernel memory by heap_bytes, the next is refused at an
                object limit equal to the use, and the drop leaves both at 0;
                timer_create on clock 2 and with option 1 is INVALID_ARGS.";
            attribute :>> parent = "H.OBJ.21";
            attribute :>> unit = ("object::timer::Timer::new", "object::timer::heap_bytes",
                "object::timer::TimerCore::now", "syscall::native::timer_create");
        }
        requirement <'L.object.214'> aSetIsOneShotInItsWindow : ItemLowLevel {
            attribute :>> statement = "timer_set shall read the deadline and slack
                whole through its pointer on every architecture; with
                TIMER_RELATIVE it shall take the deadline from the clock read once
                in the call; it shall clear READABLE, supersede the timer's
                previous arm, and arm it once for [deadline, deadline + slack]; a
                deadline at or before the clock's reading shall fire in the call;
                an unknown option shall be INVALID_ARGS, a handle that is not a
                timer WRONG_TYPE, one without WRITE ACCESS_DENIED.";
            attribute :>> criterion = "A deadline past 2^32 ns and a slack past
                2^33 ns reach the timer's window whole; a past deadline reads
                READABLE when timer_set returns, fired by no interrupt pass; the
                refusals as stated; the ABI crate's host test reads a TimerSpec
                back whole.";
            attribute :>> parent = "H.OBJ.21";
            attribute :>> unit = ("object::timer::TimerCore::set",
                "syscall::native::timer_set", "syscall::native::timer_in");
        }
        requirement <'L.object.215'> aCancelledArmNeverSignals : ItemLowLevel {
            attribute :>> statement = "timer_cancel shall clear READABLE and
                disarm the timer, so that nothing its cancelled arm filed or had in
                flight signals afterwards.";
            attribute :>> criterion = "A timer set 100 ms ahead and cancelled is
                not heard in 150 ms, reads quiet, and has its slot home; with the
                cancel's supersession taken out, the case fails with its
                sentence.";
            attribute :>> parent = "H.OBJ.21";
            attribute :>> unit = ("object::timer::TimerCore::cancel", "object::timer::TimerCore::disarm",
                "object::timer::TimerCore::supersede", "syscall::native::timer_cancel");
        }
        requirement <'L.object.216'> aFireIsTheInterruptsAndNeverEarly : ItemLowLevel {
            doc /* The fire allocates nothing: the slot, the registrations' room
                and the room for the ports it keeps are made with the timer, and
                the packet's room was promised by its registration
                (TRACEABILITY.md argues it; no allocation guard runs in the
                interrupt). */
            attribute :>> statement = "A timer's arm shall be fired only by its
                processor's timer interrupt, with no run queue's lock held, by a
                processor leaving service for what its buffer holds, or by a set
                whose deadline has passed; never before its deadline; the
                fire shall assert READABLE, deliver the registrations that want it
                and wake its waiters, allocating nothing, and one interrupt pass
                shall fire at most FIRE_BATCH arms.";
            attribute :>> criterion = "A timer set 2 ms ahead is heard on its port
                with its key, fired no earlier than 2 ms after the set, and reads
                READABLE; FIRE_BATCH + 4 timers due at once all fire, no pass
                firing more than FIRE_BATCH; with the window filed 1 ms early, or
                the buffer let past its size, the cases fail with their
                sentences.";
            attribute :>> parent = "H.OBJ.21";
            attribute :>> unit = ("object::timer::fire", "object::timer::TimerCore::signal",
                "object::timer::TimerCore::signals",
                "object::timer::TimerCore::deliver", "sched::fire_timers",
                "sched::timer_expired");
        }
        requirement <'L.object.217'> anOpenWindowFiresWithTheHead : ItemLowLevel {
            attribute :>> statement = "An arm shall be filed keyed by the latest
                instant of its window, and a sleeper set's pass shall also take an
                arm whose window has opened while it is first and the fired buffer
                has room.";
            attribute :>> criterion = "Of two timers, the second keyed 5 ms after
                the first with its window open at the first's deadline, filed in a
                sleeper set of the check's own holding nothing else, the shipped
                pass function (sched::take_next) run over that set at the first's
                deadline, not a timed interrupt, takes both, and they fire in one
                pass; with the open window not taken, the case fails with its
                sentence.";
            attribute :>> parent = "H.OBJ.21";
            attribute :>> unit = ("sched::queue::CpuQueue::wake_sleepers",
                "sched::queue::CpuQueue::sleeper_due");
        }
        requirement <'L.object.218'> timersShareTheSleeperSet : ItemLowLevel {
            attribute :>> statement = "A timer's arm shall be filed on its
                processor's sleeper set beside sleeping tasks, in a slot made with
                the timer; a pass shall move a due arm into the fixed fired buffer
                and, when the buffer is full, file it again MIN_ARM_NS on, at most
                FIRE_BATCH a pass, so that the tasks behind it are still woken;
                the timer interrupt's pass shall wake no task and stop at a due
                one, leaving it to the decision the interrupt asks for; the run
                queue shall arm its timer MIN_ARM_NS away while the buffer holds
                any.";
            attribute :>> criterion = "FIRE_BATCH + 4 timers due at once fire over
                at least two passes with none lost; an arm a pass took out is
                filed again, once, by the fire that returns its slot.";
            attribute :>> parent = "H.OBJ.21";
            attribute :>> unit = ("sched::queue::CpuQueue::wake_sleepers",
                "sched::queue::take_next", "sched::queue::place", "sched::queue::CpuQueue::take_due_timers",
                "sched::queue::Fired::new", "sched::queue::Fired::take",
                "sched::queue::CpuQueue::take_fired", "sched::queue::CpuQueue::file_timer",
                "sched::queue::CpuQueue::unfile_timer", "sched::queue::CpuQueue::arm_timer",
                "sched::file_timer_here", "sched::unfile_timer");
        }
        requirement <'L.object.219'> aSupersededArmSignalsNothing : ItemLowLevel {
            attribute :>> statement = "Every set and cancel shall move the timer to
                a new generation; a fire of an arm from an older generation shall
                signal nothing, put the slot home and file the newer arm if one
                waits, so that an arm is filed exactly once by whichever of the
                set and the fire holds the slot.";
            attribute :>> criterion = "An arm taken off its sleeper set and then
                superseded by a set signals nothing when fired; the newer arm is
                filed by that fire and heard once, no earlier than its deadline;
                with the generation not compared, the case fails with its
                sentence.";
            attribute :>> parent = "H.OBJ.21";
            attribute :>> unit = ("object::timer::fire", "object::timer::TimerCore::take_back",
                "object::timer::TimerCore::file_if_home");
        }
        requirement <'L.object.220'> aClosedTimerIsDisarmed : ItemLowLevel {
            attribute :>> statement = "The drop of a timer's last handle shall
                cancel it, wait out a delivery in flight, and let go of its
                registrations and the ports its fires kept in task context; a
                timer shall hold at most TIMER_OBSERVERS registrations, in room
                made with it, registering none past it.";
            attribute :>> criterion = "An armed, watched timer whose last handle
                closes is never heard and is freed; with the close not cancelling,
                the case fails.";
            attribute :>> parent = "H.OBJ.21";
            attribute :>> unit = ("object::timer::TimerCore::close",
                "object::timer::Timer::drop", "object::timer::TimerCore::drop",
                "object::timer::TimerCore::spend", "object::port::Observers::is_empty",
                "object::timer::TimerCore::observe", "object::port::register_within",
                "object::port::Observers::with_room", "object::port::Observer::fire_keeping");
        }
    }

    package ExceptionChannels {
        doc /* src/kernel/src/object/exception.rs and syscall/native.rs's
             * exception_channel_create: a supervisor attached to a process or
             * a job (docs/microkernel/K4.md section 2.2), and the chain a
             * fault walks to its supervisors (sections 2.3 to 2.7): trap.rs's
             * user_fault_as asks object::exception::raise before the
             * personality's signal. */

        requirement <'L.object.241'> anExceptionChannelIsAttachedOnlyBySupervise : ItemLowLevel {
            attribute :>> statement = "exception_channel_create shall attach an
                exception channel to a process, started or not, or to a job, only
                through a handle carrying SUPERVISE (else ACCESS_DENIED; any other
                object WRONG_TYPE), with a timeout in 1 to EXCEPTION_TIMEOUT_MAX_MS
                milliseconds and options 0 (else INVALID_ARGS); it shall refuse a
                second channel while one whose read end is open is attached
                (ALREADY_BOUND) and a process that has ended (BAD_STATE); it shall
                charge the channel's two ends to the caller's job and be refused
                NO_MEMORY at its object limit; a refusal shall attach nothing. The
                read end it answers shall carry DUPLICATE, TRANSFER, READ and
                WAIT and never WRITE, the kernel holding the only writing end, and
                the attach shall be audited EXCEPTION_ATTACHED.";
            attribute :>> criterion = "Stage 9's exceptions line: a job made with
                job_create and an unstarted process made with process_create are
                each attached once and a second attach is ALREADY_BOUND; a process
                handle without SUPERVISE, a Rights::JOB handle, timeouts 0 and
                EXCEPTION_TIMEOUT_MAX_MS + 1, an option bit, a VMO and a handle that
                names nothing are refused with their statuses; a write to the read
                end is ACCESS_DENIED; an attach charges 2 objects and one at the
                limit is NO_MEMORY with nothing attached.";
            attribute :>> parent = ("H.OBJ.2", "H.QUOTA.3", "H.TRAP.20");
            attribute :>> unit = ("syscall::native::exception_channel_create",
                "object::exception::Supervisor::attach");
        }
        requirement <'L.object.242'> closingTheReadEndDetaches : ItemLowLevel {
            attribute :>> statement = "An exception channel whose read end has
                closed shall no longer count as attached: the next attach to its
                process or job shall be taken, and the kernel end it held let go.
                A process's slot shall be closed as the process ends, so that its
                supervisor sees PEER_CLOSED then and an attach afterwards is
                BAD_STATE.";
            attribute :>> criterion = "Stage 9's exceptions line: after the read
                end of a job's channel is closed the slot is not live and a new
                attach is taken; a process killed with its job closes its
                supervisor's channel (PEER_CLOSED within the check's patience) and
                a later attach is BAD_STATE.";
            attribute :>> parent = ("H.OBJ.2", "H.TRAP.20");
            attribute :>> unit = ("object::exception::Supervisor::is_live",
                "object::exception::Supervisor::close",
                "object::exception::Supervisor::let_go_if_dead");
        }
        requirement <'L.object.246'> superviseIsOnlyACreators : ItemLowLevel {
            attribute :>> statement = "SUPERVISE shall be right bit 11. Only
                process_create's and job_create's handles shall carry it
                (Rights::PROCESS_CREATED, Rights::JOB_CREATED); Rights::PROCESS and
                Rights::JOB, which devmgr_start, devmgr's drivers job,
                job_for_cgroup and the root job's handles carry, shall not; a
                duplicate or a replace shall only ever remove it.";
            attribute :>> criterion = "native-abi's host test pins bit 11, ALL,
                and that PROCESS and JOB lack it; stage 9's exceptions line reads
                PROCESS_CREATED and JOB_CREATED off the handles the two calls
                answer, and a Rights::JOB handle and a duplicate narrowed to
                Rights::PROCESS are refused ACCESS_DENIED.";
            attribute :>> parent = ("H.OBJ.2", "H.TRAP.20");
            attribute :>> unit = ("syscall::native::process_create",
                "syscall::native::job_create");
        }
        requirement <'L.object.270'> regionCreateNeedsManage : ItemLowLevel {
            attribute :>> statement = "REGION_CREATE shall need MANAGE on a job, charge one object, and
                answer a region handle and its space handle.";
            attribute :>> criterion = "The check: without MANAGE, refused.";
            attribute :>> parent = "H.OBJ.26";
            attribute :>> unit = ("object::region::Region::new",
                "object::region::Region::enter");
        }
        requirement <'L.object.271'> aSharedProcessIsInTheRegionsJob : ItemLowLevel {
            attribute :>> statement = "PROCESS_CREATE_SHARED shall need MANAGE on the region and on the
                job, the job the region's or beneath it, and bind a fresh or a
                given space.";
            attribute :>> criterion = "Case 89 and the check.";
            attribute :>> parent = "H.OBJ.25";
            attribute :>> unit = ("object::bare::Bare::new",
                "object::bare::Bare::start",
                "object::bare::run_thread",
                "object::process::Process::in_region");
        }
        requirement <'L.object.272'> threadCreateIsTheCallersOwn : ItemLowLevel {
            attribute :>> statement = "THREAD_CREATE shall make a thread of the caller's own process
                alone, charged to its job, and be refused from restricted mode.";
            attribute :>> criterion = "Cases 84, 124, 127.";
            attribute :>> parent = "H.OBJ.25";
            attribute :>> unit = ("object::bare::Bare::spawn",
                "object::bare::Bare::spawn_with",
                "object::bare::Bare::spawn_placed",
                "object::bare::spawn_on",
                "object::bare::current_thread");
        }
        requirement <'L.object.273'> threadExitEndsAThreadOrAProcess : ItemLowLevel {
            attribute :>> statement = "THREAD_EXIT shall end the calling thread, or its process with the
                status, in normal mode, and be refused from restricted mode; a
                thread's handle shall see TERMINATED.";
            attribute :>> criterion = "Cases 88, 89.";
            attribute :>> parent = "H.OBJ.25";
            attribute :>> unit = ("object::bare::leave_current",
                "object::bare::Bare::thread_gone");
        }
        requirement <'L.object.274'> restrictedModeReachesThePrivateTable : ItemLowLevel {
            attribute :>> statement = "From restricted mode a handle number shall name the private table.";
            attribute :>> criterion = "Case 61.";
            attribute :>> parent = "H.OBJ.23";
            attribute :>> unit = "object::process::Process::table_of_mode";
        }
        requirement <'L.object.275'> normalModeReachesTheSharedTable : ItemLowLevel {
            attribute :>> statement = "From normal mode of a shared process a handle number shall name
                the shared table.";
            attribute :>> criterion = "Case 60 onward.";
            attribute :>> parent = "H.OBJ.23";
            attribute :>> unit = "object::process::Process::table_of_mode";
        }
        requirement <'L.object.276'> aPlainProcessHasOneTable : ItemLowLevel {
            attribute :>> statement = "A process of no region shall have one table, whatever the mode
                byte, which is never up for it.";
            attribute :>> criterion = "Every other program of the boot.";
            attribute :>> parent = "H.OBJ.23";
            attribute :>> unit = "object::process::Process::with_private_handles";
        }
        requirement <'L.object.277'> theTablesNumbersAreApart : ItemLowLevel {
            attribute :>> statement = "Neither table's numbers shall name the other's objects.";
            attribute :>> criterion = "Cases 61, 62, 64.";
            attribute :>> parent = "H.OBJ.23";
            attribute :>> unit = "object::process::Process::table_of_mode";
        }
        requirement <'L.object.278'> aMoveNeedsTransfer : ItemLowLevel {
            attribute :>> statement = "Each move shall need TRANSFER, and HANDLE_KEEP DUPLICATE as well.";
            attribute :>> criterion = "Case 68.";
            attribute :>> parent = "H.OBJ.24";
            attribute :>> unit = ("syscall::native::region::handle_to_shared",
                "syscall::native::region::handle_to_private");
        }
        requirement <'L.object.279'> aMoveCannotWiden : ItemLowLevel {
            attribute :>> statement = "A move shall give a subset of the rights held, or be refused
                INVALID_ARGS.";
            attribute :>> criterion = "Case 63.";
            attribute :>> parent = "H.OBJ.24";
            attribute :>> unit = "syscall::native::region::handle_to_shared";
        }
        requirement <'L.object.280'> aMoveTakesItFromWhereItWas : ItemLowLevel {
            attribute :>> statement = "A move shall take the handle from its table, and name only this
                process's private one.";
            attribute :>> criterion = "Cases 64, 66, 67.";
            attribute :>> parent = "H.OBJ.24";
            attribute :>> unit = "syscall::native::region::handle_to_private";
        }
        requirement <'L.object.281'> bootstrapAndGiveTables : ItemLowLevel {
            attribute :>> statement = "PROCESS_START_SHARED shall move a bootstrap handle to the shared
                table, or pass its value when it is there already.";
            attribute :>> criterion = "The check starts the program so.";
            attribute :>> parent = "H.OBJ.24";
            attribute :>> unit = "syscall::native::region::process_start_shared";
        }
        requirement <'L.object.282'> aRegionsLastProcessEmptiesItsTable : ItemLowLevel {
            attribute :>> statement = "A region's last process leaving shall empty its shared table,
                whatever is in it, and refuse any more.";
            attribute :>> criterion = "The boot goes on past the check with its frames back;
                object::region.";
            attribute :>> parent = "H.OBJ.26";
            attribute :>> unit = ("object::region::Region::leave",
                "object::bare::Bare::drop");
        }
        requirement <'L.object.283'> aHigherObjectsHandleDoesNotLand : ItemLowLevel {
            attribute :>> statement = "A handle to a process, thread, job, space, region or exception
                whose job's level is above the holder's shall not land in the
                holder's table: by a channel read, a move, a bootstrap or a
                cgroup's job.";
            attribute :>> criterion = "The `levels` line on every boot: three handles offered from level
                2 to level 0, each INVALID.";
            attribute :>> parent = "H.OBJ.34";
            attribute :>> unit = ("object::level::may_hold",
                "object::level::level_of",
                "object::exception::Exception::level",
                "object::process::Exit::level",
                "object::bare::ThreadRef::level",
                "object::space::SpaceRef::level",
                "syscall::native::transfers_refused");
        }
        requirement <'L.object.284'> aChildIsAtMostItsParent : ItemLowLevel {
            attribute :>> statement = "JOB_CREATE shall refuse a level above the parent's (ACCESS_DENIED)
                or past the top (INVALID_ARGS), and without the option the child
                takes the parent's level.";
            attribute :>> criterion = "The `levels` line on every boot.";
            attribute :>> parent = "H.OBJ.34";
            attribute :>> unit = ("object::job::Job::new_child_at",
                "object::job::Job::level",
                "syscall::native::job_level_asked");
        }
        requirement <'L.object.285'> aDomainIsOneLevel : ItemLowLevel {
            attribute :>> statement = "A speculation domain shall be one job, and so one level, and no
                process shall move into it from another.";
            attribute :>> criterion = "By the move refusal, L.object.288, under every
                partition_speculation value.";
            attribute :>> parent = "H.OBJ.34";
            attribute :>> unit = "object::job::Job::domain";
        }
        requirement <'L.object.286'> aRefusalIsAudited : ItemLowLevel {
            attribute :>> statement = "Every refusal between levels shall be recorded as LEVEL, outside
                every lock.";
            attribute :>> criterion = "The `levels` line on every boot: the record moves at each.";
            attribute :>> parent = "H.OBJ.34";
            attribute :>> unit = ("syscall::native::record_level",
                "syscall::native::may_map_at");
        }
        requirement <'L.object.287'> aLevelIsFixed : ItemLowLevel {
            attribute :>> statement = "No call shall change a job's level after it is made; a job that
                asked, and every job inside it, is declared for good.";
            attribute :>> criterion = "The `levels` line on every boot: the level and the declared mark
                read back.";
            attribute :>> parent = "H.OBJ.34";
            attribute :>> unit = ("object::job::level_declared",
                "object::job::Job::new_child_leveled");
        }
        requirement <'L.object.288'> aMoveKeepsItsLevel : ItemLowLevel {
            attribute :>> statement = "A process shall not move between jobs of different levels; one
                placed as it is made takes the level of its job; and a region shall
                take no process of another level than its job's.";
            attribute :>> criterion = "The `levels` line on every boot.";
            attribute :>> parent = "H.OBJ.34";
            attribute :>> unit = ("object::process::Process::move_charged",
                "object::process::Process::take_level_of",
                "syscall::native::region::process_create_shared");
        }
        requirement <'L.object.289'> aRefusedHandleIsDeliveredInvalid : ItemLowLevel {
            attribute :>> statement = "A channel read of a message holding a handle its reader may not
                hold shall deliver the bytes with that slot Handle::INVALID, the
                object disposed outside the lock, at final delivery alone.";
            attribute :>> criterion = "The `levels` line on every boot.";
            attribute :>> parent = "H.OBJ.34";
            attribute :>> unit = "syscall::native::deliver_some";
        }
        requirement <'L.trap.9'> theChainIsNearestFirst : ItemLowLevel {
            attribute :>> statement = "Save a machine check that cannot be restarted, which no supervisor hears, a user-mode fault its address space does not
                resolve shall be offered, before the personality's fault_signal, to
                the faulting process's channel (level 0) and then to each job's from
                the process's own to the root (levels 1 and up). A level with no
                channel whose read end is open, or whose report cannot be made or
                queued, shall be skipped, and a skip counted; the end of the chain
                shall take fault_signal as with no supervisor; a process whose end is
                recorded shall not enter the chain.";
            attribute :>> criterion = "Case d: the process's channel hears the fault
                at level 0 and, handed on, the job's at level 1 with the same pc and
                task. Case m: with no channel anywhere nothing is reported or skipped
                and the program ends with SIGSEGV.";
            attribute :>> parent = "H.TRAP.20";
            attribute :>> unit = ("object::exception::raise",
                "trap::user_fault_ending",
                "object::exception::Asked::into_raised", "trap::user_fault_as",
                "trap::user_fault",
                "object::exception::Supervisor::live");
        }
        requirement <'L.trap.10'> theWaitIsBounded : ItemLowLevel {
            attribute :>> statement = "The faulting thread shall wait for a verdict
                with interrupts open and no lock held, until a verdict, its process's
                end, or the earlier of its level's timeout and one chain deadline
                EXCEPTION_TIMEOUT_MAX_MS after the first report; a signal sent
                meanwhile shall stay pending for the way out.";
            attribute :>> criterion = "Case e: a fault on a 5 ms channel nobody reads
                ends the program no sooner than 5 ms after it started. Case e2: a
                program that is the only reader of its own job's channel is ended by
                the expiry.";
            attribute :>> parent = "H.TRAP.20";
            attribute :>> unit = "object::exception::ask";
        }
        requirement <'L.trap.11'> anExpiryIsTheDefault : ItemLowLevel {
            attribute :>> statement = "A wait that ends at its deadline undecided
                shall mark the exception expired, so that a later verdict or register
                call is refused TIMED_OUT, record EXCEPTION_KILLED with detail 2 and
                the level, and end the chain: the fault takes fault_signal, with no
                further level asked.";
            attribute :>> criterion = "Case e: the program ends KILLED by SIGSEGV;
                the last EXCEPTION_KILLED names it with 2 and level 0; the exception
                read afterwards refuses exception_resolve and exception_state
                TIMED_OUT.";
            attribute :>> parent = "H.TRAP.20";
            attribute :>> unit = ("object::exception::Chain::ask_level",
                "object::exception::killed");
        }
        requirement <'L.trap.12'> theVerdictsAreKept : ItemLowLevel {
            attribute :>> statement = "RESUME shall return to the program with the
                exception's registers through the trap's own exit, recording
                EXCEPTION_CONTEXT with both pcs when a supervisor wrote them, but
                that of a machine check at an unchanged pc shall go on to the
                signal; KILL
                shall end the process as a job kill does, recording EXCEPTION_KILLED
                with detail 1; HAND_ON, or the exception's last handle closed
                undecided, shall go to the next level.";
            attribute :>> criterion = "Case a: resumed at its exit with 42 the
                program exits 42, and EXCEPTION_CONTEXT names both pcs. Case c: KILL
                ends it KILLED by SIGKILL, recorded. Case f: closed undecided, it ends
                with SIGSEGV before the 10 s timeout. Case i: moved past its
                breakpoint it exits 97.";
            attribute :>> parent = "H.TRAP.20";
            attribute :>> unit = ("object::exception::Exception::resolve",
                "object::exception::Exception::drop", "object::exception::audit_context");
        }
        requirement <'L.trap.13'> nestingRaisesNothing : ItemLowLevel {
            attribute :>> statement = "A supervisor's own fault shall take its own
                chain; a thread shall wait on at most one exception; a report's repeat
                shall count the reports in a row its thread raised at the same pc and
                address. While a channel watches a process or a job above it, execve
                shall give it no set-id file's ids, and no cgroup.procs move or
                CLONE_INTO_CGROUP shall put a process into the subtree (EBUSY). A
                process that ran with ids it was raised to, had its ids changed, or
                made itself not dumpable shall never again have a fault offered to
                any supervisor, one attached afterwards included, and neither shall a
                fork of it or a native child it launches.";
            attribute :>> criterion = "Case k: an exception held by a supervisor
                that dies is handed on to the job's channel at once. Case l: resumed
                unchanged, repeat reads 0, 1 and 2. Case n: ids_it_may_raise gives a
                supervised process no ids and an unsupervised one the file's. Case o
                (the cgroups line): a move into a cgroup whose job holds a channel is
                EBUSY and is taken once the channel closes. Case p: a program loaded
                with a set-id file's ids is marked, and its fault, with a channel
                attached afterwards, is reported to nobody and ends with SIGSEGV.
                Cases q and r: its fork and a native child it launches are marked,
                and the native child's fault is reported to nobody.";
            attribute :>> parent = "H.TRAP.20";
            attribute :>> unit = ("object::exception::supervised",
                "object::exception::job_supervised", "object::exception::report_for",
                "object::exception::note_resumed",
                "object::exception::Supervisor::refuse",
                "object::exception::Supervisor::is_refused");
        }
        requirement <'L.trap.14'> aLinuxNumberExitsWithItsWords : ItemLowLevel {
            attribute :>> statement = "A Linux number from restricted mode shall exit with the number and
                six arguments in the registers K1 §2.2 names, the reason in the
                reason register.";
            attribute :>> criterion = "Case 20, 21.";
            attribute :>> parent = "H.TRAP.21";
            attribute :>> unit = ("arch::x86_64::restricted::from_restricted",
                "arch::x86_64::speculation::exit_barrier",
                "arch::x86_64::restricted::leave_restricted",
                "arch::x86_64::restricted::flip",
                "arch::x86_64::restricted::swap_user_state",
                "arch::x86_64::syscall::look_on_the_way_out",
                "arch::x86_64::restricted::own_state");
        }
        requirement <'L.trap.15'> aNativeNumberIsAnsweredOrExits : ItemLowLevel {
            attribute :>> statement = "A native number from restricted mode shall be answered by the row
                of nr::from_restricted: against the private table in place, by an
                exit (PORT_FD), or refused BAD_STATE with the thread staying; a
                value with high bits set is a Linux number.";
            attribute :>> criterion = "Cases 52 to 55.";
            attribute :>> parent = "H.TRAP.21";
            attribute :>> unit = "arch::x86_64::restricted::store_syscall";
        }
        requirement <'L.trap.16'> anUnresolvedFaultExits : ItemLowLevel {
            attribute :>> statement = "An unresolved fault from restricted mode shall exit FAULT with its
                vector, code, address and kind, ahead of any supervisor, and a
                resolvable one shall not exit.";
            attribute :>> criterion = "Cases 30 to 37.";
            attribute :>> parent = "H.TRAP.21";
            attribute :>> unit = ("arch::x86_64::restricted::fault_exit",
                "arch::x86_64::restricted::exit_from_trap",
                "trap::restricted_fault_kind", "trap::exit_on_fault");
        }
        requirement <'L.trap.17'> aKickExitsARunningThread : ItemLowLevel {
            attribute :>> statement = "A kick shall exit a thread running in restricted mode. Needs
                SIGNAL.";
            attribute :>> criterion = "Cases 84, 85.";
            attribute :>> parent = "H.TRAP.21";
            attribute :>> unit = ("arch::x86_64::restricted::kick_on_trap_frame",
                "arch::x86_64::restricted::kick_on_syscall_frame");
        }
        requirement <'L.trap.18'> aKickInNormalModeWaits : ItemLowLevel {
            attribute :>> statement = "A kick to a thread in normal mode shall exit its next entry, which
                runs no instruction of the program.";
            attribute :>> criterion = "Case 86.";
            attribute :>> parent = "H.TRAP.21";
            attribute :>> unit = ("arch::x86_64::restricted::answer_going_in",
                "arch::x86_64::restricted::write_exit");
        }
        requirement <'L.trap.19'> normalModeIsAsItWas : ItemLowLevel {
            attribute :>> statement = "Normal mode's stack pointer, callee-saved registers and FS and GS
                at the return shall be those of the call, but for the reason
                register.";
            attribute :>> criterion = "Every case runs Rust across each exit.";
            attribute :>> parent = "H.TRAP.21";
            attribute :>> unit = "arch::x86_64::restricted::answer_going_in";
        }
        requirement <'L.trap.20'> resumeOnlyAfterASystemCall : ItemLowLevel {
            attribute :>> statement = "RESTRICTED_RESUME shall be refused BAD_STATE with no context held,
                or unless the last exit was a system call exit, with the reason
                register left zero.";
            attribute :>> criterion = "Cases 26, 27.";
            attribute :>> parent = "H.TRAP.21";
            attribute :>> unit = "arch::x86_64::restricted::prepare";
        }
        requirement <'L.trap.21'> normalCallsAreRefusedFromRestrictedMode : ItemLowLevel {
            attribute :>> statement = "A call nr::from_restricted marks normal-only, made from restricted
                mode, shall be refused BAD_STATE, and the thread shall stay in
                restricted mode.";
            attribute :>> criterion = "Case 53.";
            attribute :>> parent = "H.TRAP.21";
            attribute :>> unit = "arch::x86_64::restricted::from_restricted";
        }
        requirement <'L.trap.22'> aPreemptedProgramComesBack : ItemLowLevel {
            attribute :>> statement = "The kernel's preemption of a thread in restricted mode shall
                resume it on the restricted root with its registers.";
            attribute :>> criterion = "Cases 124 to 126: a spinner preempted many times exits only by its
                kick.";
            attribute :>> parent = "H.TRAP.21";
            attribute :>> unit = ("user::space::AddressSpace::install_as",
                "smp::PerCpu::set_task_kind");
        }
        requirement <'L.trap.23'> vectorsAreTheProgramsOwn : ItemLowLevel {
            attribute :>> statement = "A program's vector registers shall be the same after an exit and
                an entry whatever normal mode did to its own.";
            attribute :>> criterion = "Cases 74 to 76.";
            attribute :>> parent = "H.TRAP.24";
            attribute :>> unit = ("arch::x86_64::restricted::vector_bytes",
                "arch::x86_64::restricted::set_vector_bytes",
                "arch::x86_64::switch::UserState::vector_image",
                "arch::x86_64::switch::UserState::set_vector_image");
        }
        requirement <'L.trap.24'> aCopyFaultLandsAndNoOtherDoes : ItemLowLevel {
            attribute :>> statement = "A page fault in normal mode, on the restricted half, unresolved,
                with the instruction pointer in the region's copy window, shall
                resume at the window's landing with only the fault's kind written;
                any other normal-mode fault goes to K4's chain and past it ends
                the region's job.";
            attribute :>> criterion = "Cases 70 to 72; the fault of the second process in case 89.";
            attribute :>> parent = "H.TRAP.21";
            attribute :>> unit = ("arch::x86_64::restricted::land_copy",
                "trap::copy_landing",
                "trap::restricted_fault",
                "object::region::Region::set_window",
                "object::region::Region::landing_for",
                "object::bare::fault_signal");
        }
        requirement <'L.trap.30'> aContextMayAskEveryCallToExit : ItemLowLevel {
            attribute :>> statement = "A context entered with ENTER_ALL_CALLS_EXIT shall exit on a native
                number as on any other, answering nothing, until the next entry, and an
                unknown option shall be refused.";
            attribute :>> criterion = "Case 145.";
            attribute :>> parent = "H.TRAP.21";
            attribute :>> unit = ("arch::x86_64::restricted::all_calls_exit",
                "arch::aarch64::restricted::all_calls_exit");
        }
        requirement <'L.user.190'> aCallsCopyMissMayExit : ItemLowLevel {
            attribute :>> statement = "A context entered with ENTER_COPY_MISS_EXITS, whose answered
                call answers FAULT because its copy missed the thread's own restricted space and
                whose row in copy_miss may run again, shall exit with the kernel's kind CallCopy,
                the registers as at the call and the pc back at it, before anything of the answer
                is written, and CONTINUE shall run it again; with the option down the call shall
                answer FAULT, and an unknown option shall be refused before anything is taken.";
            attribute :>> criterion = "Cases 146, 147, 148, 152.";
            attribute :>> parent = "H.TRAP.21";
            attribute :>> unit = ("arch::x86_64::restricted::call_copy_exit",
                "arch::aarch64::restricted::call_copy_exit");
        }
        requirement <'L.user.191'> aMissIsTheThreadsOwnSpaces : ItemLowLevel {
            attribute :>> statement = "A failed copy shall be noted as a miss only with the option
                up and only in the running thread's own restricted space, and a failure the call
                goes on past shall not stay noted, so that a FAULT from another cause exits never.";
            attribute :>> criterion = "Case 151, and no path reaches the guard today, so it is shown with a plant: read_target, in restricted mode, through a faulting copy of the target's space, mkm-cm7-plant-x and -a holding the case, and with the guard taken away mkm-cm7-own-x and -a failing it (ledger 6677).";
            attribute :>> parent = "H.TRAP.21";
            attribute :>> unit = ("arch::x86_64::restricted::note_copy_miss",
                "arch::aarch64::restricted::note_copy_miss",
                "arch::x86_64::restricted::forget_copy_miss",
                "arch::aarch64::restricted::forget_copy_miss",
                "syscall::uaccess::forget_copy_miss");
        }
        requirement <'L.user.192'> aCallThatTookSomethingRestoresIt : ItemLowLevel {
            attribute :>> statement = "A call whose row in copy_miss is Restores shall give back what
                it took when its copy fails, so that the run again finds it.";
            attribute :>> criterion = "Cases 149, 150.";
            attribute :>> parent = "H.TRAP.21";
            attribute :>> unit = ("syscall::native::port_wait",);
        }
        requirement <'L.trap.25'> aKillEndsAThreadInEitherMode : ItemLowLevel {
            attribute :>> statement = "A job kill shall end a thread of a process of a region in either
                mode.";
            attribute :>> criterion = "Cases 133, 134. That an end posted as a thread goes in is taken before
                the flip, with interrupts masked, is by review of answer_going_in's
                must_leave look (ledger 6282 R6, B7), which no case can time.";
            attribute :>> parent = "H.TRAP.21";
            attribute :>> unit = ("object::bare::Bare::end",
                "object::bare::Bare::release",
                "object::bare::return_to_user",
                "object::bare::leave_current",
                "object::bare::ThreadRef::mark_ended");
        }
        requirement <'L.trap.26'> aKickEndsARestrictedWait : ItemLowLevel {
            attribute :>> statement = "A kick shall end a blocking native call from restricted mode with
                INTERRUPTED in the result register, then an exit.";
            attribute :>> criterion = "Case 127.";
            attribute :>> parent = "H.TRAP.21";
            attribute :>> unit = "sched::work::take_kick";
        }
        requirement <'L.trap.27'> manyKicksAreOneExit : ItemLowLevel {
            attribute :>> statement = "Any number of kicks before an exit shall be one exit, and the exit
                shall lower the mark.";
            attribute :>> criterion = "Case 87.";
            attribute :>> parent = "H.TRAP.21";
            attribute :>> unit = "sched::work::take_kick";
        }
        requirement <'L.trap.28'> continueReentersUnchanged : ItemLowLevel {
            attribute :>> statement = "RESTRICTED_CONTINUE shall re-enter the held context as it stands,
                and a RESTRICTED_CONTEXT_READ of a context whose flags a program
                set shall be accepted by RESTRICTED_ENTER, normalised.";
            attribute :>> criterion = "Cases 58, 59.";
            attribute :>> parent = "H.TRAP.21";
            attribute :>> unit = ("arch::x86_64::restricted::read_context",
                "arch::x86_64::restricted::context_bytes");
        }
        requirement <'L.trap.29'> everyNativeNumberHasARow : ItemLowLevel {
            attribute :>> statement = "Every native call shall have a row in nr::from_restricted, an
                exhaustive match.";
            attribute :>> criterion = "The build: a call with no row does not compile.";
            attribute :>> parent = "H.TRAP.21";
            attribute :>> unit = "arch::x86_64::restricted::from_restricted";
        }
        requirement <'L.object.243'> aReportIsTheKernels : ItemLowLevel {
            attribute :>> statement = "A report shall be 64 bytes the kernel writes,
                every field its own: the kind, the level, the process, the task, the
                job, the address, the architecture's code, the pc and the flags; the
                message shall carry exactly one exception handle, with EXCEPTION:
                TRANSFER, READ, WRITE and MANAGE, never DUPLICATE. Once K6's attested
                sender is on main, the report's sender shall read as the kernel.";
            attribute :>> criterion = "Case a: a store through null is reported as a
                write page fault at address 0, level 0, in its job, its pc at the
                store; its handle carries EXCEPTION and handle_duplicate is
                ACCESS_DENIED. Case i: a breakpoint carries the architecture's code.";
            attribute :>> parent = ("H.TRAP.20", "H.OBJ.2");
            attribute :>> unit = ("object::exception::make",
                "object::exception::report_for");
        }
        requirement <'L.object.244'> registersAreCheckedBeforeStored : ItemLowLevel {
            attribute :>> statement = "exception_state shall copy the faulting
                thread's registers out with READ, or replace them with WRITE only
                after the architecture's rule has accepted every field, a refusal
                INVALID_ARGS changing nothing; an unknown op or a length other than
                the register set's shall be INVALID_ARGS; a decided exception
                BAD_STATE and an expired one TIMED_OUT.";
            attribute :>> criterion = "Case b on every architecture: each forged set
                is refused and the registers read back unchanged; each set a program
                may hold is taken and reads back as written. Case h: op 2 and a short
                length are INVALID_ARGS.";
            attribute :>> parent = ("H.TRAP.20", "H.OBJ.2");
            attribute :>> unit = ("syscall::native::exception_state",
                "object::exception::Exception::registers",
                "object::exception::Exception::set_registers",
                "object::exception::pending");
        }
        requirement <'L.object.245'> aVerdictIsGivenOnce : ItemLowLevel {
            attribute :>> statement = "exception_resolve shall take RESUME, KILL or
                HAND_ON with MANAGE, once, while the exception is pending: a second
                BAD_STATE, one after expiry TIMED_OUT, any other verdict
                INVALID_ARGS, any other object WRONG_TYPE.";
            attribute :>> criterion = "Case h: a second verdict is BAD_STATE, verdict
                3 INVALID_ARGS, a channel WRONG_TYPE. Case e: a verdict after expiry
                is TIMED_OUT.";
            attribute :>> parent = ("H.TRAP.20", "H.OBJ.2");
            attribute :>> unit = "syscall::native::exception_resolve";
        }
    }

    package AddressWaitCalls {
        doc /* K5's native calls, 0x106B to 0x106E (docs/microkernel/K5.md
             * section 3): their decoding and refusals, over the core's table
             * (L.user.135-144). */

        requirement <'L.object.203'> addressWaitDecodes : ItemLowLevel {
            attribute :>> statement = "address_wait shall refuse a flag other than
                ADDRESS_SHARED and ADDRESS_BY_VMO, a zero bitset, a misaligned word
                and a value or bitset wider than 32 bits with INVALID_ARGS; by handle,
                need a VMO handle with READ and refuse an offset whose word passes
                the VMO's end with INVALID_ARGS; and answer a wait's end as
                SHOULD_WAIT, TIMED_OUT, EINTR, NO_MEMORY or FAULT.";
            attribute :>> criterion = "The refusals of the `addrwait` line, each with
                its status; a wait by mapping and by handle each woken.";
            attribute :>> parent = ("H.OBJ.20", "H.OBJ.1", "H.OBJ.2");
            attribute :>> unit = ("syscall::native::address_wait",
                "syscall::native::address_word", "syscall::native::address_status",
                "syscall::native::word_argument", "syscall::native::address_deadline");
        }
        requirement <'L.object.204'> addressWakeDecodes : ItemLowLevel {
            attribute :>> statement = "address_wake shall take the same flags and
                refusals as address_wait, wake at most its 32-bit count, and answer
                how many it woke.";
            attribute :>> criterion = "A wake of zero, two, and by bitset answer 0, 2
                and 1; a wake with a handle without READ is ACCESS_DENIED (the
                `addrwait` line).";
            attribute :>> parent = ("H.OBJ.20", "H.OBJ.2");
            attribute :>> unit = "syscall::native::address_wake";
        }
        requirement <'L.object.205'> addressRequeueDecodes : ItemLowLevel {
            attribute :>> statement = "address_requeue shall take ADDRESS_SHARED and
                ADDRESS_COMPARE and refuse ADDRESS_BY_VMO and any other flag, a
                misaligned word and a count or value wider than 32 bits with
                INVALID_ARGS, and answer how many it woke or moved.";
            attribute :>> criterion = "A requeue by handle and a misaligned one are
                INVALID_ARGS; a requeue of two answers 2 (the `addrwait` line).";
            attribute :>> parent = "H.OBJ.20";
            attribute :>> unit = "syscall::native::address_requeue";
        }
        requirement <'L.object.206'> addressWaitAnyDecodes : ItemLowLevel {
            attribute :>> statement = "address_wait_any shall refuse call flags, no
                words, more than ADDRESS_WAIT_ANY_MAX words and a null vector with
                INVALID_ARGS; read the vector of 16-byte AddressWord elements, each
                word's flags ADDRESS_SHARED or none; and answer the index of the
                word woken.";
            attribute :>> criterion = "A wait on no words, on 129, with call flags or
                with a word by handle is INVALID_ARGS; a wait on three answers 1 for
                the second (the `addrwait` line).";
            attribute :>> parent = "H.OBJ.20";
            attribute :>> unit = "syscall::native::address_wait_any";
        }
    }

    package SpacesByHandle {
        doc /* K2 of docs/MICROKERNEL.md section 3: an address space named by a
             * handle (docs/microkernel/K2.md, slice A; the consultant's OK IF,
             * ledger 2845 and 2857). Stage 9's `space` line verifies each,
             * through the architecture's system call entry. */

        requirement <'L.object.232'> aMadeSpaceIsEmptyAndItsMakers : ItemLowLevel {
            attribute :>> statement = "space_create shall make an empty address space
                and answer a handle carrying Rights::SPACE, the space one native
                object charged to the caller's job, which owns it.";
            attribute :>> criterion = "A made space has no region, and the caller's
                job's object count rose by exactly one.";
            attribute :>> parent = "H.MEM.24";
            attribute :>> unit = ("syscall::native::space_create",
                "object::space::SpaceRef::create");
        }
        requirement <'L.object.290'> processMakeMakesAnEmptyProcess : ItemLowLevel {
            attribute :>> statement = "process_make shall need MANAGE on the job, keep a sealed creator inside its tree, refuse a name past PROCESS_NAME_MAX, and answer a handle with Rights::PROCESS_CREATED to an unstarted process in the job, its space empty, audited PROCESS_MADE, and in a measured job shall measure the space before the caller hears of it.";
            attribute :>> criterion = "The process's space has no region and the handle reads PROCESS_CREATED; without MANAGE ACCESS_DENIED, a long name INVALID_ARGS, a sealed member outside its tree ACCESS_DENIED (the `build` line).";
            attribute :>> parent = "H.OBJ.27";
            attribute :>> unit = ("syscall::native::process_make", "syscall::native::new_process_handle");
        }

        requirement <'L.object.291'> processRunIsJudgedLikeAStart : ItemLowLevel {
            attribute :>> statement = "process_run shall need MANAGE, answer BAD_STATE once started, and a refused bootstrap shall move nothing and give the start back.";
            attribute :>> criterion = "A WAIT-only handle ACCESS_DENIED; a bootstrap that is no handle BAD_HANDLE and a later run succeeds; a second run BAD_STATE (the `build` line).";
            attribute :>> parent = "H.OBJ.27";
            attribute :>> unit = ("syscall::native::process_run", "syscall::native::start_with");
        }

        requirement <'L.object.292'> processRunChecksEntryAndStack : ItemLowLevel {
            attribute :>> statement = "process_run shall refuse an entry at or past the end of user space, or a stack past it, with INVALID_ARGS before anything is claimed.";
            attribute :>> criterion = "Four entries and two stacks outside user space, each INVALID_ARGS, on every architecture, and the machine runs on (the `build` line).";
            attribute :>> parent = "H.OBJ.27";
            attribute :>> unit = ("syscall::native::process_run", "syscall::native::in_user_space");
        }

        requirement <'L.object.293'> aProcessEntersWhereItIsTold : ItemLowLevel {
            attribute :>> statement = "A process process_run started shall enter at the entry, on the stack, with the bootstrap's value in its first argument register.";
            attribute :>> criterion = "A program that exits with its stack pointer's page number exits with the stack's; one that exits with its argument exits with the bootstrap's value (the `build` line).";
            attribute :>> parent = "H.OBJ.27";
            attribute :>> unit = ("syscall::native::process_run", "syscall::native::start_with");
        }

        requirement <'L.object.294'> anEmptySpaceOnlyEndsTheChild : ItemLowLevel {
            attribute :>> statement = "A process run with nothing mapped at its entry shall end by its own fault, and nothing else shall stop; a job at its memory limit may build a process that then ends at a text fault.";
            attribute :>> criterion = "An empty process run ends with a non-zero status and the check goes on; a child whose job's limit was lowered after its build ends at its first fault (the `build` line).";
            attribute :>> parent = "H.OBJ.27";
            attribute :>> unit = ("syscall::native::process_run", "syscall::native::process_make");
        }

        requirement <'L.object.295'> theOldCallsAreCompiledOut : ItemLowLevel {
            attribute :>> statement = "In a kernel built with personality=user, process_create and process_start shall answer ENOSYS.";
            attribute :>> criterion = "The case in syscall/region_check.rs under that flag, run by every personality=user boot (test-first-processes --personality user), and its control with the comparison inverted (ledger 7558).";
            attribute :>> parent = "H.OBJ.27";
            attribute :>> unit = ("syscall::native::job_call");
        }

        requirement <'L.object.296'> nothingOfASpaceThroughAStartedHandle : ItemLowLevel {
            attribute :>> statement = "After process_run, process_space on the process shall answer BAD_STATE, so a creator holds its space only by a handle it took before the start.";
            attribute :>> criterion = "process_space after a run BAD_STATE (the `build` line).";
            attribute :>> parent = "H.OBJ.27";
            attribute :>> unit = ("syscall::native::process_space");
        }

        requirement <'L.object.299'> noPagerRefusesAPagerVmo : ItemLowLevel {
            attribute :>> statement = "space_map with MAP_NO_PAGER shall refuse a pager-backed VMO with WRONG_TYPE and map any other.";
            attribute :>> criterion = "The refusal and the map (the `build` line).";
            attribute :>> parent = "H.OBJ.27";
            attribute :>> unit = ("syscall::native::space_map");
        }

        requirement <'L.object.306'> theImageRights : ItemLowLevel {
            attribute :>> statement = "The kernel shall hand devmgr each image with READ, MAP, EXECUTE and TRANSFER, neither WRITE nor DUPLICATE.";
            attribute :>> criterion = "image_rights() is IMAGE_RIGHTS, which holds no WRITE or DUPLICATE (the `build` line).";
            attribute :>> parent = "H.OBJ.27";
            attribute :>> unit = ("discovery::devmgr::image_rights");
        }

        requirement <'L.object.300'> aPagerHasOneKeeper : ItemLowLevel {
            attribute :>> statement = "pager_keep shall need PAGER on the pager and answer at most one keeper for it, with exactly Rights::KEEPER, charged to the caller's job as one object and the registry's heap; a keeper's close on a live pager shall change nothing else.";
            attribute :>> criterion = "A second keep ALREADY_BOUND; the rights read exactly; a keeper closed on a live pager and the pager still serves (the `rebind` line).";
            attribute :>> parent = "H.OBJ.28";
            attribute :>> unit = ("object::pager::Pager::keep", "syscall::native::pager_keep");
        }

        requirement <'L.object.301'> aParkedPagerEndsNothing : ItemLowLevel {
            attribute :>> statement = "With a keeper the pager's close shall end no request, and a request opened while parked shall be listed and send no packet; live, parked and dead shall be decided under the registry's lock.";
            attribute :>> criterion = "Read and dirty waits across a close stay waiting; a copy's fault while parked is listed with no packet (the `rebind` line).";
            attribute :>> parent = "H.OBJ.28";
            attribute :>> unit = ("object::pager::PagerCore::close", "object::pager::PagerCore::current", "object::pager::PagerCore::list_or_join", "object::pager::PagerLink::open_or_join");
        }

        requirement <'L.object.302'> aTakeUpSendsEachAgain : ItemLowLevel {
            attribute :>> statement = "pager_take_up shall need MANAGE on the keeper and WRITE on the port, refuse a pager not parked with BAD_STATE, leave it parked on NO_MEMORY, send each open request to the new port under its own id, and audit the take-up.";
            attribute :>> criterion = "The packets on the new port carry the old ids; a supply by the new handle answers the clients; a second take-up BAD_STATE; the same port handed back in a second cycle (the `rebind` line).";
            attribute :>> parent = "H.OBJ.28";
            attribute :>> unit = ("object::pager::Keeper::take_up", "object::pager::Request::send", "object::pager::record_rebind", "syscall::native::pager_take_up");
        }

        requirement <'L.object.303'> aParkedWaitIsBounded : ItemLowLevel {
            attribute :>> statement = "A wait on a parked pager shall stay bounded by each waiter's own bound from when it began to wait, and shall end at its process's end.";
            attribute :>> criterion = "At a 5 ms bound with no take-up the wait ends SIGBUS never before the bound; a waiter killed while parked leaves (the `rebind` line).";
            attribute :>> parent = "H.OBJ.28";
            attribute :>> unit = ("object::pager::PagerLink::request", "object::pager::PagerLink::wait");
        }

        requirement <'L.object.304'> aKeepersCloseEndsAParkedPager : ItemLowLevel {
            attribute :>> statement = "A keeper's close while the pager is parked shall be the pager's death: every request ends at once and no request opens after.";
            attribute :>> criterion = "A parked waiter ends SIGBUS within 5 s of the keeper's close, far below its bound (the `rebind` line).";
            attribute :>> parent = "H.OBJ.28";
            attribute :>> unit = ("object::pager::PagerCore::keeper_closed", "object::pager::Keeper::drop");
        }

        requirement <'L.object.305'> parkedStateStaysCharged : ItemLowLevel {
            attribute :>> statement = "A request's record shall stay charged to the job whose fault opened it across a park and a take-up.";
            attribute :>> criterion = "The faulting job's memory holds the record while parked and after the take-up (the `rebind` line).";
            attribute :>> parent = "H.OBJ.28";
            attribute :>> unit = ("object::pager::PagerLink::request", "object::pager::Keeper::take_up");
        }

        requirement <'L.object.307'> dirtyStaysAcrossARestart : ItemLowLevel {
            attribute :>> statement = "A page Dirty before a restart shall stay reported to the next instance.";
            attribute :>> criterion = "pager_query_dirty by the new handle reports the page (the `rebind` line).";
            attribute :>> parent = "H.OBJ.28";
            attribute :>> unit = ("object::pager::Keeper::take_up");
        }

        requirement <'L.object.233'> onlyTheCreatorBeforeTheStart : ItemLowLevel {
            attribute :>> statement = "process_space shall answer a handle to the
                address space of a process process_create made, through a handle
                that carries MANAGE and the process's Control, before the process
                starts, with rights a subset of Rights::SPACE and owned by the
                process's job; it shall refuse ACCESS_DENIED without MANAGE or
                Control, BAD_STATE once the process has started or ended, and
                INVALID_ARGS for a right a space does not carry. A space handle
                taken before the start shall keep its rights after it.";
            attribute :>> criterion = "Before the start a full and a READ-only
                handle are given; a handle with WAIT alone and a process handle
                with no Control are ACCESS_DENIED; READ with MANAGE is
                INVALID_ARGS; after the start process_space is BAD_STATE, and the
                READ-only handle from before it reads the running child's text.";
            attribute :>> parent = "H.MEM.24";
            attribute :>> unit = ("syscall::native::process_space",
                "object::process::Control::is_unstarted", "object::space::SpaceRef::of");
        }
        requirement <'L.object.234'> anExecutableMappingNeedsBothHandles : ItemLowLevel {
            attribute :>> statement = "space_map shall map a VMO shared into the space
                its handle names with MAP on the space and MAP and READ on the VMO,
                WRITE on the VMO for a writable mapping, and EXECUTE on both handles
                for an executable one, and shall refuse a writable and executable
                protection, or any bit outside MAP_READ, MAP_WRITE and MAP_EXECUTE,
                with INVALID_ARGS before it looks at a handle.";
            attribute :>> criterion = "A VMO's bytes read back through a mapping by
                handle; an executable mapping is ACCESS_DENIED through a VMO handle
                without EXECUTE and through a space handle without it, and made
                through both; a writable and executable protection is
                INVALID_ARGS; a mapping without MAP is ACCESS_DENIED.";
            attribute :>> parent = "H.MEM.24";
            attribute :>> unit = ("syscall::native::space_map",
                "syscall::native::space_protection", "syscall::native::vmo_held",
                "syscall::native::space_in");
        }
        requirement <'L.object.235'> anUnmapByHandleNeedsMap : ItemLowLevel {
            attribute :>> statement = "space_unmap shall unmap whatever lies in a
                whole-page range of the space its handle names, with MAP, and
                refuse a range that is not whole pages with INVALID_ARGS.";
            attribute :>> criterion = "Without MAP the unmap is ACCESS_DENIED; with
                it, a mapped page is gone and a read of it by handle is FAULT.";
            attribute :>> parent = "H.MEM.24";
            attribute :>> unit = "syscall::native::space_unmap";
        }
        requirement <'L.object.236'> aProtectionStaysWithinItsHandle : ItemLowLevel {
            attribute :>> statement = "space_protect shall change the protection only
                of a range every region of which a handle mapped, within the
                protection each region's handle allowed, executable only with
                EXECUTE on the space handle, and never writable and executable; it
                shall refuse a range reaching a region no handle mapped with
                BAD_STATE and a protection past a region's ceiling with
                ACCESS_DENIED, changing nothing.";
            attribute :>> criterion = "A region from a read-only VMO handle made
                writable, one from an executable handle made writable, and one
                from a handle without EXECUTE made executable are each
                ACCESS_DENIED; a writable region made read-only and back is
                allowed; a program's own region is BAD_STATE; the bytes read back
                unchanged after the refusals.";
            attribute :>> parent = "H.MEM.24";
            attribute :>> unit = ("syscall::native::space_protect",
                "user::space::AddressSpace::protect_by_handle", "user::space::within_ceilings");
        }
        requirement <'L.object.237'> privateMemoryByHandle : ItemLowLevel {
            attribute :>> statement = "space_allocate shall map fresh private
                anonymous memory, zero until written, into the space its handle
                names, with MAP, executable only with EXECUTE on the space handle,
                never writable and executable (INVALID_ARGS), and refuse a range
                over a mapping with INVALID_ARGS.";
            attribute :>> criterion = "An executable allocation through a space
                handle without EXECUTE is ACCESS_DENIED; a writable and executable
                one INVALID_ARGS; a read-write one is made where asked and reads
                zero; a second over it is INVALID_ARGS.";
            attribute :>> parent = "H.MEM.24";
            attribute :>> unit = ("syscall::native::space_allocate",
                "user::space::AddressSpace::allocate_by_handle");
        }
        requirement <'L.object.238'> aCopyByHandleNeedsItsRightAndChargesTheOwner : ItemLowLevel {
            attribute :>> statement = "space_read shall copy at most SPACE_COPY_MAX
                bytes out of the space its handle names, with READ, and space_write
                into it, with WRITE, each honouring each region's protection, short
                at the first page it cannot copy and FAULT if that is the first; a
                page either faults in, and a copy-on-write copy a write makes, shall
                be charged to the space's owner and never to the caller, and at the
                owner's limit either shall answer NO_MEMORY with nothing killed.";
            attribute :>> criterion = "Without READ a read, and without WRITE a
                write, is ACCESS_DENIED; a read across a mapping's end is short; a
                read and a write of an untouched page of a created process's space
                each raise the owner's job's memory by at least a page and leave the
                caller's job's unchanged; with the owner's limit at its use the next
                read and the next write are NO_MEMORY, the OOM kill count and the
                caller's memory unchanged.";
            attribute :>> parent = "H.MEM.24";
            attribute :>> unit = ("syscall::native::space_read",
                "syscall::native::space_write", "syscall::native::read_target",
                "syscall::native::write_target", "syscall::native::space_step",
                "object::space::SpaceRef::charging_owner", "object::quota::charging_to");
        }
        requirement <'L.object.239'> aCloneCarriesItsSourcesRights : ItemLowLevel {
            attribute :>> statement = "space_clone shall answer a copy-on-write clone
                of the space its handle names, with READ, through a handle carrying
                exactly the rights the given handle carries, the clone one native
                object owned by the caller's job.";
            attribute :>> criterion = "A clone of a READ and MAP handle carries READ
                and MAP and nothing else; a clone through a handle without READ is
                ACCESS_DENIED.";
            attribute :>> parent = ("H.MEM.24", "H.MEM.25");
            attribute :>> unit = ("syscall::native::space_clone",
                "syscall::native::space_held", "object::space::SpaceRef::clone_space");
        }
        requirement <'L.object.297'> protectionZeroIsAllocateOnly : ItemLowLevel {
            attribute :>> statement = "space_allocate with protection 0 shall make a
                private region with no access; space_map and space_protect shall
                refuse protection 0 with INVALID_ARGS.";
            attribute :>> criterion = "Stage 9's space line: a read through the handle
                gets nothing of such a region, and the two other calls refuse it.
                Control: protection 0 treated as MAP_READ.";
            attribute :>> parent = ("H.MEM.24", "H.MEM.25");
            attribute :>> unit = ("syscall::native::space_allocate",
                "syscall::native::space_protection",
                "user::space::AddressSpace::allocate_by_handle");
        }
        requirement <'L.object.310'> aLiftCallAnswersItsHandleAlone : ItemLowLevel {
            attribute :>> statement = "Each of linuxd's calls (M5-LIFT.md §2) shall refuse a handle that
                is absent, of the wrong kind or short of the call's right, and
                shall answer ENOSYS in a kernel other than personality=user.";
            attribute :>> criterion = "test-linuxd's `lift-calls 19 refusals held`. Controls: mkl-c-holds,
                mkl-c-r5.";
            attribute :>> parent = ("H.OBJ.30");
            attribute :>> unit = ("syscall::native::lift::call");
        }
        requirement <'L.object.311'> aWindowIsItsOwnMapping : ItemLowLevel {
            attribute :>> statement = "A space opened as a window shall take no mapping by the calls that
                name a region, and every byte placed in it shall lie in the window.";
            attribute :>> criterion = "lift-calls' window refusals; SPACE_MAP, SPACE_WRITE and SPACE_CLONE
                refuse it. Control: mkl-c-wmap.";
            attribute :>> parent = ("H.OBJ.30");
            attribute :>> unit = ("user::space::AddressSpace::open_window",
                "user::space::AddressSpace::with_placed",
                "user::space::AddressSpace::window_take_down",
                "mm::unmap_placed");
        }
        requirement <'L.object.312'> placedFramesAreTheHandlesOwn : ItemLowLevel {
            attribute :>> statement = "SPACE_PLACE shall place only pages of the VMO the handle names,
                never writable and executable at once, execute only through a handle
                that carries EXECUTE, and shall mark the VMO's pages as held.";
            attribute :>> criterion = "lift-calls' place refusals. Control: mkl-c-wx.";
            attribute :>> parent = ("H.OBJ.30");
            attribute :>> unit = ("user::space::AddressSpace::place",
                "user::vmo::Vmo::mark_placed");
        }
        requirement <'L.object.313'> aCopyMissComesBackToItsServer : ItemLowLevel {
            attribute :>> statement = "A kernel copy from a restricted program's memory that misses shall
                come back to the region's server as a fault to fill, the copy rewound, and
                its status shall not reach the program until the fill failed.";
            attribute :>> criterion = "test-threads under personality=user: a copy into a page not yet
                placed. Control: mkl-c-rewind.";
            attribute :>> parent = ("H.OBJ.30");
            attribute :>> unit = ("arch::x86_64::restricted::note_copy_miss",
                "arch::x86_64::restricted::forget_copy_miss",
                "arch::x86_64::restricted::call_copy_exit");
        }
        requirement <'L.object.315'> aClockReadAnswersWhatEl0CannotAsk : ItemLowLevel {
            attribute :>> statement = "CLOCK_READ, under personality=user alone, shall answer 3
                and 4 with the kernel's hwcaps for a program and 5 with the processor the caller
                was on, a stale hint by its return, and a question it does not know with
                INVALID_ARGS.";
            attribute :>> criterion = "lift/core/calls_check.rs: each question answered and the
                processor below the count, an unknown one refused, the hwcaps nonzero on AArch64, on
                x86-64 and AArch64. Controls: an unknown question answered, 5 past the last. In
                the baseline: its unit is the item's, its check the lift crate's, which the tag
                scan does not read (ledger 7126).";
            attribute :>> parent = ("H.OBJ.30");
            attribute :>> unit = ("syscall::native::lift::call");
        }
        requirement <'L.object.314'> aFaultsNeighboursAreOnlyWhatIsResident : ItemLowLevel {
            attribute :>> statement = "Under fault_ahead=on a fault shall bring in only pages the region's
                object already holds, or a run of fresh memory, each with no more than its own
                rights, under the space's lock; a neighbour's refusal shall not be the program's.";
            attribute :>> criterion = "test-threads' `fault-ahead` under personality=user (ledger 6537,
                A1-A7).";
            attribute :>> parent = ("H.OBJ.30");
            attribute :>> unit = ("user::space::AddressSpace::fault_around",
                "user::space::AddressSpace::write_ahead");
        }
        requirement <'L.object.309'> aSpaceHandleStopsARaise : ItemLowLevel {
            attribute :>> statement = "While a space handle names a process's space,
                raises_refused shall say so, and execve shall give it no ids for any
                set-id file; the count shall fall as handles close, and nothing but a
                process not yet started shall raise it.";
            attribute :>> criterion = "Stage 9's space line: a process with a handle
                kept is not raised and with it closed is; a fork made while one lived
                is raised, its space its own; a native child with a handle taken
                before its start is not, until the handle closes. Control: the test
                removed from ids_it_may_raise.";
            attribute :>> parent = ("H.MEM.24", "H.MEM.25");
            attribute :>> unit = ("user::space::AddressSpace::raises_refused",
                "user::space::AddressSpace::handle_made",
                "user::space::AddressSpace::handle_gone",
                "object::space::SpaceRef::of");
        }
        requirement <'L.object.240'> anExecutableVmoHandleCannotWrite : ItemLowLevel {
            attribute :>> statement = "vmo_executable shall replace a VMO handle that
                carries MAP and READ with one that carries EXECUTE and not WRITE,
                closing the one it took, and change nothing when it refuses;
                vmo_create shall give no EXECUTE, and no duplicate shall add it.";
            attribute :>> criterion = "The replaced handle is BAD_HANDLE, the new one
                is refused vmo_write with ACCESS_DENIED and maps executable; a
                duplicate asking EXECUTE of a plain VMO handle is ACCESS_DENIED.";
            attribute :>> parent = "H.MEM.24";
            attribute :>> unit = "syscall::native::vmo_executable";
        }
    }

    package Pagers {
        doc /* src/kernel/src/syscall/native.rs's pager calls, 0x1074 to
             * 0x1078, and the page-request packet (docs/microkernel/K3.md
             * section 4; the consultant's OK IF, ledger 2858). */

        requirement <'L.object.226'> aPagerHasOneHandle : ItemLowLevel {
            attribute :>> statement = "pager_create shall take a port with WRITE
                and a bound read whole through a pointer, clamped to 1 ms and 30 s
                with 0 the maximum, refuse any option, charge one object and its
                heap to the caller's job, and give one handle with TRANSFER and
                PAGER and no DUPLICATE.";
            attribute :>> criterion = "Stage 9's pager check: an option and a VMO as
                the port are refused; a duplicate of the pager's handle is
                ACCESS_DENIED; a bound of 0 is 30 s, of 1 ns is 1 ms, of 5 ms is 5
                ms.";
            attribute :>> parent = "H.MEM.22";
            attribute :>> unit = ("syscall::native::pager_create", "object::pager::Pager::new",
                "syscall::native::read_words", "syscall::native::pager_in");
        }
        requirement <'L.object.227'> aPagerVmoIsMadeOverItsPager : ItemLowLevel {
            attribute :>> statement = "pager_create_vmo shall need PAGER, read its
                key, size and options whole, refuse an unknown option or no pages,
                and make a VMO that is pager-backed and not anonymous for life,
                which is never pinned and never grows.";
            attribute :>> criterion = "Stage 9's pager check: an unknown option is
                refused; a supply naming another pager's VMO is refused, and the
                pager VMO is refused as an aux VMO.";
            attribute :>> parent = "H.MEM.22";
            attribute :>> unit = ("syscall::native::pager_create_vmo",
                "object::pager::PagerCore::link", "user::vmo::Vmo::new_paged",
                "user::vmo::Vmo::grow_to", "syscall::native::unpaged_vmo_in");
        }
        requirement <'L.object.228'> aSupplyIsChecked : ItemLowLevel {
            attribute :>> statement = "pager_supply shall need PAGER on the pager
                and READ and WRITE on the aux VMO, refuse with BAD_STATE a VMO not
                this pager's, an aux VMO that is not anonymous, an uncommitted or
                held aux page and a detached VMO, with INVALID_ARGS an unaligned or
                out-of-range range or an option, and change nothing when it
                refuses.";
            attribute :>> criterion = "Stage 9's pager check: nine refusals, each
                with its status, the pager VMO's page still absent and the aux page
                still in the aux VMO.";
            attribute :>> parent = "H.MEM.22";
            attribute :>> unit = ("syscall::native::pager_supply",
                "syscall::native::pager_and_vmo", "syscall::native::page_range",
                "object::pager::PagerCore::serves");
        }
        requirement <'L.object.229'> aPagerOpIsChecked : ItemLowLevel {
            attribute :>> statement = "pager_op shall need PAGER and the VMO to be
                the pager's, refuse an unknown operation, a FAIL errno other than
                EIO or ENOSPC, a value or request id given to any other operation,
                and DIRTY over an absent page; pager_query_dirty shall report
                exactly the Dirty and awaiting-clean runs of its range, lowest
                first.";
            attribute :>> criterion = "Stage 9's pager check: an unknown operation,
                errno 7 and DIRTY of an absent page are refused; the query after a
                trap-dirty write shows that page alone as Dirty.";
            attribute :>> parent = "H.MEM.23";
            attribute :>> unit = ("syscall::native::pager_op",
                "syscall::native::pager_query_dirty", "syscall::native::pager_call",
                "syscall::native::pager_fail", "syscall::native::pager_page_op");
        }
        requirement <'L.object.230'> aPageRequestSaysWhatItAsks : ItemLowLevel {
            attribute :>> statement = "A page request's packet shall carry the VMO's
                key, kind PACKET_PAGE_REQUEST, its command in the low byte of its
                signals word and the run's length in pages above it, the run's
                first byte offset, and the request's id, never 0 and never reused.";
            attribute :>> criterion = "Stage 9's pager check: the read packet for a
                fault on page 2 of 8 says READ, 6 pages, offset 8192 and a nonzero
                id; a trap-dirty write's says DIRTY, 1 page.";
            attribute :>> parent = "H.MEM.22";
            attribute :>> unit = ("object::pager::PagerLink::request",
                "object::pager::Command::number");
        }
        requirement <'L.object.231'> noPagerMapsWhenAsked : ItemLowLevel {
            attribute :>> statement = "vmo_map and space_map with MAP_NO_PAGER
                shall refuse a pager-backed VMO with WRONG_TYPE, and map any other VMO
                as without it.";
            attribute :>> criterion = "Stage 9's pager check: a pager VMO is refused
                WRONG_TYPE and an anonymous one mapped, both with MAP_NO_PAGER, by
                either call.";
            attribute :>> parent = "H.MEM.22";
            attribute :>> unit = ("syscall::native::vmo_map", "syscall::native::space_map");
        }
        requirement <'L.object.320'> firstProcessesStartMeasured : ItemLowLevel {
            attribute :>> statement = "The manager and each partition it starts shall start measured, in a
                sealed job, from a sealed image whose digest is on its record, before
                devmgr and linuxd.";
            attribute :>> criterion = "test-first-processes: its lines, in that order, and the manager's
                comparison of the record with the description.";
            attribute :>> parent = "H.DEV.12";
            attribute :>> unit = ("boot_authority::run", "boot_authority::try_start_manager");
        }
        requirement <'L.object.321'> firstProcessesHoldTheirRows : ItemLowLevel {
            attribute :>> statement = "Before each first process runs, the kernel shall hold what that process
                is about to hold against its role's const table, by kind, rights and number, from the objects
                themselves, none being the root job, and shall stop the boot on a miss.";
            attribute :>> criterion = "Every personality=user boot runs it; test-first-processes, and a control
                giving one handle more, which stops the boot; check-first-rows.py holds the tables to the design.";
            attribute :>> parent = "H.DEV.13";
            attribute :>> unit = ("first_rows::Rows::judge", "first_rows::Rows::of");
        }
        requirement <'L.object.322'> noSafetyDeviceToDevmgr : ItemLowLevel {
            attribute :>> statement = "A device a description names shall not be in devmgr's DEVICES.";
            attribute :>> criterion = "test-first-processes: 1 kept back, with the filter removed it fails.";
            attribute :>> parent = "H.DEV.12";
            attribute :>> unit = ("boot_authority::held_by_manager", "iommu::would_translate");
        }
        requirement <'L.object.323'> aBadDescriptionStopsTheBoot : ItemLowLevel {
            attribute :>> statement = "A description naming no real device, or malformed, shall stop the
                boot.";
            attribute :>> criterion = "test-first-processes: a made-up location and a truncated file, each
                stopping it with its reason.";
            attribute :>> parent = "H.DEV.12";
            attribute :>> unit = ("boot_authority::node_of", "boot_authority::start_manager");
        }
        requirement <'L.object.326'> theManagersDeathStopsTheMachine : ItemLowLevel {
            attribute :>> statement = "The manager's end, a clean exit included, shall stop the machine with
                FX-0954.";
            attribute :>> criterion = "test-first-processes: an image ending at once in its place.";
            attribute :>> parent = "H.DEV.13";
            attribute :>> unit = "boot_authority::watch_manager";
        }
        requirement <'L.object.328'> devmgrsDeathQuiesces : ItemLowLevel {
            attribute :>> statement = "devmgr's end shall kill the drivers' job and quiesce every device not
                a safety partition's; a dead driver's pins stay quarantined.";
            attribute :>> criterion = "test-first-processes: an image ending at once in devmgr's place, and
                the kernel's line.";
            attribute :>> parent = "H.DEV.13";
            attribute :>> unit = "discovery::devmgr::watch_detached";
        }
        requirement <'L.object.334'> firstImagesFromSealed : ItemLowLevel {
            attribute :>> statement = "A first process's pages shall be made by the kernel from the bytes of
                its sealed image, no other copy, and that image's digest recorded on its measured space: the
                one exception to executable only from sealed.";
            attribute :>> criterion = "test-first-processes boots the manager and devmgr so measured;
                review of boot_authority::load_sealed, its one caller each.";
            attribute :>> parent = "H.DEV.13";
            attribute :>> unit = "boot_authority::load_sealed";
        }
        requirement <'L.object.335'> theKernelsCpioWalk : ItemLowLevel {
            attribute :>> statement = "ferrix_cpio::file_named shall answer the regular file of a safe name,
                inside the archive's bounds, stop at the first malformed header, allocate nothing and write
                nothing: ring 0's one parser of the archive under personality=user.";
            attribute :>> criterion = "ferrix-cpio's host tests of it, its fuzz target, and a refused
                archive's boot in test-first-processes.";
            attribute :>> parent = "H.DEV.13";
            attribute :>> unit = "ferrix_cpio::file_named";
        }
        requirement <'L.object.327'> linuxdsDeathKillsItsJob : ItemLowLevel {
            attribute :>> statement = "linuxd's end shall kill what remains of its partition's job.";
            attribute :>> criterion = "test-partitions: a partition's linuxd dying, its line with the count.";
            attribute :>> parent = "H.DEV.13";
            attribute :>> unit = ("linuxd_start::start", "linuxd_start::start_further");
        }
        requirement <'L.object.336'> aPostSealRequestWithNoPromiseIsRefused : ItemLowLevel {
            attribute :>> statement = "After the seal a request charged to a job with no promise shall be refused.";
            attribute :>> criterion = "mm::seal::check's plant, on a job of its own; its control FIRED.";
            attribute :>> parent = "H.MEM.32";
            attribute :>> unit = ("mm::seal::route", "mm::seal::note_shared");
            attribute :>> scope = "kernel_memory=retyped";
        }
        requirement <'L.object.337'> anObjectIsOnItsJobsPage : ItemLowLevel {
            attribute :>> statement = "An object shall be on a page of the promise of the job it is charged to.";
            attribute :>> criterion = "mm::seal::check, against the job's draws_from; its control FIRED.";
            attribute :>> parent = "H.MEM.32";
            attribute :>> unit = "mm::heap_drawn_from";
            attribute :>> scope = "kernel_memory=retyped";
        }
        requirement <'L.object.338'> aKernelTaskChargesNobody : ItemLowLevel {
            attribute :>> statement = "A task with no job and no ticket shall draw on the pool, whichever job the
                processor last ran, and nothing shall be served in an interrupt.";
            attribute :>> criterion = "mm::seal::check with the processor's group forced to another job's; its control FIRED.";
            attribute :>> parent = "H.MEM.32";
            attribute :>> unit = ("mm::seal::charged", "mm::seal::note_payer", "mm::seal::seal_after_boot", "mm::seal::report");
            attribute :>> scope = "kernel_memory=retyped";
        }
        requirement <'L.object.340'> aFrameGoesBackWithNothingOnIt : ItemLowLevel {
            attribute :>> statement = "A frame a job's heap gives back shall hold none of that job's bytes.";
            attribute :>> criterion = "mm::seal::check's large allocation; its control FIRED.";
            attribute :>> parent = "H.MEM.32";
            attribute :>> unit = "mm::ReservedPages::deallocate_pages";
            attribute :>> scope = "kernel_memory=retyped";
        }
        requirement <'L.object.346'> aFurtherPartitionHoldsItsRow : ItemLowLevel {
            attribute :>> statement = "A further Linux partition shall be started in a job and a region of its own with the
                FURTHER row alone: no console, no cores, no devmgr channel, and its end shall kill its job and nothing else.";
            attribute :>> criterion = "test-partitions: a second partition runs programs and ends, and one that dies at once, the
                first going on; Rows::judge at its start; the first's end ends the machine, shown.";
            attribute :>> parent = "H.DEV.13";
            attribute :>> unit = "linuxd_start::start_further";
        }
        requirement <'L.object.347'> eachPartitionASpeculationDomain : ItemLowLevel {
            attribute :>> statement = "With more than one Linux partition, each shall be a speculation domain of its own.";
            attribute :>> criterion = "test-partitions reads two distinct non-zero domains from the kernel's lines; n10 FIRED.";
            attribute :>> parent = "H.DEV.13";
            attribute :>> unit = "linuxd_start::start";
        }
        requirement <'L.object.370'> aHeapChargeReclaimsFirst : ItemLowLevel {
            attribute :>> statement = "A kernel-heap charge refused at a job's memory
                limit, made for the running task's own job where it may block and not
                inside a reclaim, shall first reclaim clean cache charged to the job
                whose limit is full or beneath it and then be tried once more. In linuxd
                (the lift) such a charge shall be refused without a reclaim, as before:
                the lift's may_block answers yes whatever is held, so the charge could not
                tell a context holding a spin lock from one holding none.";
            attribute :>> criterion = "test-container's heap-reclaim step: at memory.max
                beside the cgroup's file cache, 128 opens of memory.events held and a read
                given, pgscan moving, and the file's own mapping reading as before once
                its pages were taken down and filled again; with the reclaim taken out the
                step fails on its refusal sentence (mki3f-c1, FIRED).";
            attribute :>> parent = "H.QUOTA.7";
            attribute :>> unit = ("object::quota::KernelHeap::charge",
                "object::oom::reclaim_within", "sched::heap_charge_may_reclaim");
        }
        requirement <'L.object.371'> aReclaimNeverNests : ItemLowLevel {
            attribute :>> statement = "A reclaim begun inside a reclaim of the same task
                shall stop the machine (FX-0973).";
            attribute :>> criterion = "With KernelHeap's guard taken out and a refused
                charge planted at the head of the reclaim, test-container stops as
                FX-0973, 'a reclaim began inside a reclaim' (mki3f-c2, FIRED).";
            attribute :>> parent = "H.QUOTA.7";
            attribute :>> unit = "user::cache::reclaim";
        }
    }
}
