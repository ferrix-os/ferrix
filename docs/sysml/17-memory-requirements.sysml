/*
 * Ferrix — SysML v2 model, part 17: the low-level requirements of memory.
 *
 * What each unit of the item's memory management does, as `ItemLowLevel`
 * requirements (part 13 defines the format, part 14 is the pilot this
 * copies), in two id spaces.
 *
 *  - `L.mm.<n>`: the kernel's own memory -- src/kernel/src/mm.rs and mm/ (the
 *    frame allocator's glue, the heap, the kernel's page tables, the
 *    allocation reserve, page tables unlinked and waiting for their
 *    shootdown), vmap.rs (the kernel address arena, device windows and
 *    kernel stacks) and early.rs (the mapper stage 1 runs before there is an
 *    allocator);
 *  - `L.user.<n>`: what a program's memory is made of -- src/kernel/src/user/
 *    vmo.rs (memory objects: their pages, copy-on-write, sharing and
 *    retirement) and user/space.rs (address spaces: mappings, faults,
 *    protection, unmapping and its shootdown, and the charge for them).
 *
 * Two id spaces rather than one, because they are two layers: nothing in
 * `L.user` is reached before the kernel's own memory is up, and a check of a
 * user address space is not evidence for the kernel's. Ids are flat within
 * each, the package gives the file, and they are never renumbered once a
 * check names them.
 *
 * L.user.173 was reserved for the tmpfs root's release after a switch to a
 * root disk (docs/RAM-RELEASE.md §2) and released unwritten: that is
 * fs/mod.rs and ferrix-vfs, the load ring and no ring, and no item code
 * relies on what the tmpfs holds after it (consultant ruling, ledger 5038).
 *
 * The frame, heap, paging and vma arithmetic itself is src/lib/kernel/frame,
 * heap, paging and vma, whose host tests verify it; nothing here restates
 * them. What is here is what the kernel does with them.
 *
 * The pilot's rules hold: a requirement names every function that carries
 * its behaviour; it is no broader than one check can prove, and where the
 * checks that exist each prove a part it is split; an accessor needs no
 * requirement of its own; and check code living in a product file is listed
 * in tools/common/data/traceability-units.json, not required.
 */
package FerrixMemoryRequirements {
    private import FerrixItemRequirements::*;

    package MemoryManagement {
        doc /* src/kernel/src/mm.rs: the frame allocator's interface, the kernel heap's
             * page supply and allocator, the kernel's and other trees' page tables,
             * and frame zeroing and copying. The buddy allocator and the heap
             * themselves are src/lib/kernel/frame and src/lib/kernel/heap, whose host tests
             * prove them; nothing here restates them. The frame windows at the end
             * of the file serve the checks only (mm-draft-A-notes.md). */

        requirement <'L.mm.1'> initGivesTheAllocatorTheUsableRam : ItemLowLevel {
            attribute :>> statement = "init shall give the frame allocator every frame
                firmware reported usable below the direct map's limit, except frame 0
                and the pages the per-frame array occupies, and shall refuse a memory
                map with no usable RAM, or with no usable region inside the direct map
                that holds the array, before it hands anything over.";
            attribute :>> criterion = "For memory maps built for the purpose, the
                frames the allocator manages equal the usable frames below the direct
                map's limit less frame 0 and the array's pages, 0 more and 0 fewer; a
                map with no usable region is refused NoUsableMemory and one whose
                usable regions are all smaller than the array NoRoomForPageArray.";
            attribute :>> parent = "H.MEM.14";
            attribute :>> unit = ("mm::init", "mm::place_page_array",
                "mm::insert_region", "mm::lowest_ram_frame", "mm::MemoryError::fmt");
        }
        requirement <'L.mm.2'> frameZeroIsNeverHandedOut : ItemLowLevel {
            attribute :>> statement = "init shall leave frame 0 out of the frames it
                gives the allocator, on every architecture, so that physical address 0
                is never handed out (FX-0601).";
            attribute :>> criterion = "After memory bring-up the allocator records
                frame 0 as Reserved or holds no record of it, and a request for a frame
                lying below frame 1 is refused.";
            attribute :>> parent = "H.MEM.14";
            attribute :>> unit = ("mm::init", "mm::insert_region");
        }
        requirement <'L.mm.3'> aFrameHasOneHolder : ItemLowLevel {
            attribute :>> statement = "allocate_frames shall not hand out a frame a
                live allocation holds, and shall align a block of 2^order frames to
                2^order frames.";
            attribute :>> criterion = "Two single frames taken in turn are different
                frames, and a block of order 4 starts on a multiple of 16 frames.";
            attribute :>> parent = "H.MEM.14";
            attribute :>> unit = ("mm::allocate_frames", "mm::with_frames");
        }
        requirement <'L.mm.4'> freedBlocksComeBack : ItemLowLevel {
            attribute :>> statement = "deallocate_frames shall return every block
                allocate_frames handed out to the free frames, whatever order blocks of
                different sizes are given back in.";
            attribute :>> criterion = "16 rounds of up to 256 blocks of orders 0 to 4,
                each round giving back every other block first and then the rest, leave
                the free frame count exactly where it started.";
            attribute :>> parent = "H.MEM.9";
            attribute :>> unit = ("mm::allocate_frames", "mm::deallocate_frames");
        }
        requirement <'L.mm.5'> aRunIsWholeBlocks : ItemLowLevel {
            attribute :>> statement = "allocate_frame_run shall hand out blocks of
                2^MAX_ORDER frames lying back to back, each an allocated block that can
                be given back on its own.";
            attribute :>> criterion = "A run of 2 blocks has both block heads
                allocated and each is given back alone with deallocate_frames; the
                frame count user/check.rs's run takes around the stage 6 checks comes
                back to where it started.";
            attribute :>> parent = "H.MEM.14";
            attribute :>> unit = ("mm::allocate_frame_run", "mm::deallocate_frames");
        }
        requirement <'L.mm.6'> aSplitBlockIsSingleFrames : ItemLowLevel {
            attribute :>> statement = "split_frames shall turn an allocated block into
                single allocated frames, each of which release_frame gives back on its
                own.";
            attribute :>> criterion = "A block of 2 frames split with split_frames
                leaves both frames allocated, and release_frame of each answers that it
                went back to the allocator, 2 of 2.";
            attribute :>> parent = "H.MEM.9";
            attribute :>> unit = ("mm::split_frames", "mm::release_frame");
        }
        requirement <'L.mm.7'> aSharedFrameOutlivesOneHolder : ItemLowLevel {
            attribute :>> statement = "share_frame shall count another reference to a
                frame, and release_frame shall return the frame to the allocator only
                when it drops the last reference, answering whether it did.";
            attribute :>> criterion = "A page committed to a VMO and shared once reads
                2 references; with the VMO dropped it reads 1 and the held frame count
                is one below its start; release_frame of the last reference answers
                true and the count is back where it started.";
            attribute :>> parent = "H.MEM.9";
            attribute :>> unit = ("mm::share_frame", "mm::release_frame",
                "mm::frame_references");
        }
        requirement <'L.mm.8'> userFramesAreChargedToTheirJob : ItemLowLevel {
            attribute :>> statement = "allocate_user_frame shall charge the frame to
                the running task's job, refusing the frame when the charge is refused,
                and the frame's release shall take the charge back from that job.";
            attribute :>> criterion = "Faults made as a task of a job limited to 48
                pages are refused at exactly its limit while a sibling job faults 48
                pages in, and with both spaces dropped every job's memory reads 0.";
            attribute :>> parent = ("H.QUOTA.2", "H.QUOTA.4");
            attribute :>> unit = ("mm::allocate_user_frame", "mm::release_frame",
                "mm::deallocate_frames", "mm::allocate_user_run");
        }
        requirement <'L.mm.9'> userTablesAreChargedToTheirJob : ItemLowLevel {
            attribute :>> statement = "A page table map_in makes for a user mapping
                shall be charged to the running task's job, refused with the mapping
                when the charge is refused, and the charge taken back when the table is
                freed.";
            attribute :>> criterion = "A user mapping made as a task of a job, needing
                N new page tables, raises the job's memory by N pages beyond its frames;
                at a limit one page short of them it is refused, 0 tables left made;
                with the tree torn down the job's memory reads 0.";
            attribute :>> parent = ("H.QUOTA.2", "H.QUOTA.4");
            attribute :>> unit = ("mm::ChargedTables::allocate_table", "mm::map_in",
                "mm::deallocate_frames");
        }
        requirement <'L.mm.10'> aDisownedFrameIsChargedToNobody : ItemLowLevel {
            attribute :>> statement = "disown_frame shall take a held frame's charge
                off the job it was charged to and leave the frame allocated and charged
                to nobody.";
            attribute :>> criterion = "A frame allocated as a task of a job and then
                disowned leaves the job's memory where it was before the allocation,
                the frame still allocated; its release afterwards changes no job's
                memory.";
            attribute :>> parent = ("H.QUOTA.4", "H.DMA.4");
            attribute :>> unit = "mm::disown_frame";
        }
        requirement <'L.mm.11'> lowFramesStayBelowTheirLimit : ItemLowLevel {
            attribute :>> statement = "allocate_frames_below shall hand out a block
                lying wholly below the frame limit it is given, or none.";
            attribute :>> criterion = "Every block of orders 0 to 2 taken below a
                limit of 256 frames ends at or below frame 256, until a request is
                refused; all of them given back, the free count is unchanged.";
            attribute :>> parent = "H.MEM.14";
            attribute :>> unit = "mm::allocate_frames_below";
        }
        requirement <'L.mm.12'> theHeapHoldsWhatIsPutInIt : ItemLowLevel {
            attribute :>> statement = "The kernel heap shall hand each allocation a
                block that holds what is written to it until it is freed, through
                growth and reallocation.";
            attribute :>> criterion = "A Box holds the value put in it; a Vec pushed
                to 4096 values through its reallocations holds each value at its index;
                a BTreeMap given 2048 inserts returns every value it holds under the key
                it was inserted with; and the heap has taken at least one page.";
            attribute :>> parent = "H.MEM.14";
            attribute :>> unit = ("mm::KernelAllocator::alloc",
                "mm::KernelAllocator::dealloc", "mm::KernelPages::allocate_pages",
                "mm::KernelPages::read_link", "mm::KernelPages::write_link",
                "mm::with_heap");
        }
        requirement <'L.mm.13'> theHeapGivesItsPagesBack : ItemLowLevel {
            attribute :>> statement = "The kernel heap shall count every freed block
                as free and give the slab pages it no longer needs back to the frame
                allocator, keeping at most one per size class.";
            attribute :>> criterion = "Around the heap check -- a Box, a Vec grown to
                4096 values and a BTreeMap of 2048 inserts, all dropped -- the heap's
                live bytes come back to what they were, and its pages grow by no more
                than ferrix_heap::CLASSES.";
            attribute :>> parent = "H.MEM.9";
            attribute :>> unit = ("mm::KernelAllocator::dealloc",
                "mm::KernelPages::deallocate_pages", "mm::heap_allocated",
                "mm::heap_pages");
        }
        requirement <'L.mm.14'> aRefusedAllocationIsNullAndCounted : ItemLowLevel {
            attribute :>> statement = "KernelAllocator::alloc shall answer an
                allocation that neither the heap nor an open section's reserve can
                serve with a null pointer, and count it as a refusal.";
            attribute :>> criterion = "With the heap unable to take a page and no
                section open, a fallible allocation is refused AllocError and
                heap_refusals rises by exactly 1; the heap's live bytes are unchanged.";
            attribute :>> parent = "H.MEM.11";
            attribute :>> unit = ("mm::KernelAllocator::alloc", "mm::heap_refusals");
        }
        requirement <'L.mm.15'> pageTablesAreZeroed : ItemLowLevel {
            attribute :>> statement = "A page table the kernel's mapper is given, for
                the kernel's own tables or another tree's, shall hold only zeros.";
            attribute :>> criterion = "A frame filled with a pattern and given back is
                claimed again as a new table by a mapping; all 512 of its descriptors
                other than the one the mapping wrote read 0.";
            attribute :>> parent = "H.MEM.6";
            attribute :>> unit = ("mm::KernelPhysMem::allocate_table",
                "mm::ChargedTables::allocate_table");
        }
        requirement <'L.mm.16'> zeroFrameClearsTheWholeFrame : ItemLowLevel {
            attribute :>> statement = "zero_frame shall write zero to every byte of
                the frame it is given.";
            attribute :>> criterion = "A frame filled with a non-zero pattern and
                passed to zero_frame reads 0 in 4096 of its 4096 bytes.";
            attribute :>> parent = "H.MEM.6";
            attribute :>> unit = "mm::zero_frame";
        }
        requirement <'L.mm.17'> copyFrameCopiesTheWholeFrame : ItemLowLevel {
            attribute :>> statement = "copy_frame shall make every byte of the
                destination frame equal to the same byte of the source.";
            attribute :>> criterion = "A frame filled with a pattern that differs at
                every word, copied to a frame filled with another, reads the first
                pattern in 4096 of its 4096 bytes, and the source is unchanged.";
            attribute :>> parent = "H.MEM.8";
            attribute :>> unit = "mm::copy_frame";
        }
        requirement <'L.mm.18'> demandPagesAreMappedOnFault : ItemLowLevel {
            attribute :>> statement = "map_demand_page shall resolve a kernel fault in
                the on-demand window by mapping one fresh frame at the faulting page,
                so that the access completes when it is retried.";
            attribute :>> criterion = "Writes to 3 unmapped pages of the window, out of
                order, each fault once, read back what was written and leave a mapping,
                consuming between 3 and 6 frames; a fourth into a region whose tables
                exist costs exactly 1 frame.";
            attribute :>> parent = "H.MEM.15";
            attribute :>> unit = ("mm::map_demand_page", "mm::is_demand_window");
        }
        requirement <'L.mm.19'> translateInAgreesWithTheProcessor : ItemLowLevel {
            attribute :>> statement = "translate_in shall answer, for an address in a
                tree, the physical address the processor reaches through that address
                while the tree is installed.";
            attribute :>> criterion = "In each of the 2 rounds
                check_the_processor_walks_an_installed_space runs, a value written
                through each of a two-page space's user addresses, the space installed,
                is read back through it and at the frame translate_in names for it
                through the direct map, 2 of 2 pages.";
            attribute :>> parent = "H.MEM.1";
            attribute :>> unit = ("mm::translate_in", "mm::KernelPhysMem::read");
        }
        requirement <'L.mm.20'> mapInMapsWhatItIsAsked : ItemLowLevel {
            attribute :>> statement = "map_in shall map len bytes, rounded up to whole
                pages, at virt onto phys in the tree rooted at root, with the
                permissions asked for, and nothing else.";
            attribute :>> criterion = "A mapping of 3 pages made with map_in into an
                empty tree translates each page to phys plus its offset with the flags
                asked for, and the pages before and after it do not translate.";
            attribute :>> parent = "H.MEM.15";
            attribute :>> unit = ("mm::map_in", "mm::KernelPhysMem::write",
                "mm::KernelPhysMem::allocate_table");
        }
        requirement <'L.mm.21'> userCodeIsFetchedAsWritten : ItemLowLevel {
            attribute :>> statement = "Before it maps a range user-executable, map_in
                shall make what was written to its frames through the direct map what
                every processor fetches from them.";
            attribute :>> criterion = "On each architecture and on a multi-core Arm
                board, code written into a frame through the direct map, then mapped
                user-executable with map_in and run by a program on another processor,
                returns the value the new code computes, N of N runs.";
            attribute :>> parent = "H.MEM.15";
            attribute :>> unit = "mm::map_in";
        }
        requirement <'L.mm.22'> kernelSlotsAreShared : ItemLowLevel {
            attribute :>> statement = "share_kernel_slots shall make the given top
                level slots of a tree point where the kernel root's do.";
            attribute :>> criterion = "On x86-64, every upper-half slot of a new
                address space's root equals the kernel root's, and a kernel address
                translates through the new root to what it does through the kernel's.";
            attribute :>> parent = "H.MEM.2";
            attribute :>> unit = "mm::share_kernel_slots";
        }
        requirement <'L.mm.23'> unmapInHoldsItsTablesForTheShootdown : ItemLowLevel {
            attribute :>> statement = "unmap_in shall take a mapping down from a live
                tree and put every page table the removal empties on the shootdown's
                list, giving none of them back itself (finding F-36).";
            attribute :>> criterion = "An unmap_in of the one page mapped in a fresh
                tree's user half leaves the page untranslated, lists at least one
                emptied table, counts 0 user tables given back, and leaves every listed
                table allocated: claim_frame refuses each.";
            attribute :>> parent = "H.MEM.7";
            attribute :>> unit = ("mm::unmap_in", "mm::unlinked::UnlinkedTables::push");
        }
        requirement <'L.mm.24'> unwalkedTablesGoBackAtOnce : ItemLowLevel {
            attribute :>> statement = "unmap_unwalked shall take a mapping down from a
                tree no processor can walk and give every page table the removal
                empties back to the frame allocator before it returns.";
            attribute :>> criterion = "A 3-page mapping made in a fresh tree and taken
                down with unmap_unwalked leaves nothing translating, raises the user
                tables given back by the tables the mapping made, and the free frame
                count returns to what it was before the mapping.";
            attribute :>> parent = "H.MEM.9";
            attribute :>> unit = "mm::unmap_unwalked";
        }
        requirement <'L.mm.25'> pruneInGivesBackEmptyTables : ItemLowLevel {
            attribute :>> statement = "prune_in shall give back every page table in
                the range of a tree that maps nothing, and no table that maps
                something.";
            attribute :>> criterion = "In a tree where a map_in failed part way,
                leaving tables above the page it could not map, prune_in over the range
                gives back exactly those tables, and a page mapped elsewhere in the tree
                still translates.";
            attribute :>> parent = ("H.MEM.9", "H.MEM.11");
            attribute :>> unit = "mm::prune_in";
        }
        requirement <'L.mm.26'> ioPagesTranslateWhileMapped : ItemLowLevel {
            attribute :>> statement = "map_io shall map one 4 KiB page at an I/O
                address in an IOMMU tree, with no block mapping, so that translate_io
                walking the tree as the unit does finds that page there.";
            attribute :>> criterion = "Two frames mapped into a translated domain are
                each found by translate_io at their own I/O address, and every leaf of
                the domain's tree is 4 KiB.";
            attribute :>> parent = "H.DMA.3";
            attribute :>> unit = ("mm::map_io", "mm::translate_io");
        }
        requirement <'L.mm.27'> ioTablesWaitForTheUnit : ItemLowLevel {
            attribute :>> statement = "unmap_io shall take the page down and put every
                page table the removal empties on the caller's list, giving none of
                them back itself.";
            attribute :>> criterion = "An unmap_io of the one page mapped in a domain's
                tree leaves it untranslated by translate_io, lists at least one emptied
                table, and every listed table is still allocated until the list is
                released.";
            attribute :>> parent = "H.DMA.3";
            attribute :>> unit = "mm::unmap_io";
        }
        requirement <'L.mm.28'> aKernelUnmapIsSeenEverywhere : ItemLowLevel {
            attribute :>> statement = "When unmap_kernel returns, no online processor
                shall still reach the range through the mapping it removed.";
            attribute :>> criterion = "Over 20 rounds in which every online processor
                reads a kernel page and the page is then moved to another frame with
                unmap_kernel and map_kernel, every processor reads the page's new value
                each round: 0 reads through a stale translation.";
            attribute :>> parent = "H.MEM.12";
            attribute :>> unit = ("mm::unmap_kernel", "mm::unmap_kernel_all",
                "mm::unmap_and_release", "mm::map_kernel", "mm::with_tables");
        }
        requirement <'L.mm.29'> aKernelUnmapReleasesAfterItsShootdown : ItemLowLevel {
            attribute :>> statement = "unmap_and_release shall hand the caller the
                frames a kernel unmap removed, and give back the page tables it
                emptied, only after the shootdown covering the removal has returned,
                an unmap that failed part way included.";
            attribute :>> criterion = "For an unmap of a vmap allocation, every frame
                passed to the release closure and every table given back is passed or
                given after the shootdown count has risen by one, 0 before; the same
                for an unmap made to fail part way.";
            attribute :>> parent = "H.MEM.17";
            attribute :>> unit = ("mm::unmap_and_release", "mm::Deferred::push");
        }
        requirement <'L.mm.30'> aKernelUnmapNeedsNoMemory : ItemLowLevel {
            attribute :>> statement = "unmap_kernel_all shall make room for all it may
                release before it unmaps anything and, with no room, unmap in pieces of
                at most 32 pages, each shot down and released before the next, losing
                nothing it releases.";
            attribute :>> criterion = "An unmap of a 100-page vmap allocation with
                every fallible allocation failing removes all 100 pages, gives every
                frame and table back (0 frames kept, LOST_TO_UNMAPS 0) and takes at
                least 4 shootdowns.";
            attribute :>> parent = ("H.MEM.11", "H.MEM.9");
            attribute :>> unit = ("mm::unmap_kernel_all", "mm::unmap_kernel_in_pieces",
                "mm::Deferred::make_room", "mm::Deferred::push");
        }
        requirement <'L.mm.31'> protectChangesTheTables : ItemLowLevel {
            attribute :>> statement = "protect_kernel shall change what an existing
                kernel mapping permits in the page tables themselves, leaving it
                mapped.";
            attribute :>> criterion = "A fresh vmap page's leaf reads writable;
                protected KERNEL_RODATA it reads not writable and still translates; and
                protecting it KERNEL_DATA again is accepted.";
            attribute :>> parent = "H.MEM.15";
            attribute :>> unit = ("mm::protect_kernel", "mm::with_tables");
        }
        requirement <'L.mm.32'> noKernelMappingIsWritableAndExecutable : ItemLowLevel {
            attribute :>> statement = "Once bring-up has dropped the loader's identity
                map, no leaf under the kernel's root, nor under the identity map's own
                root where the architecture has one, shall be both writable and
                executable.";
            attribute :>> criterion = "The sweep of every leaf under those roots, after
                the identity map is dropped, counts N leaves, E > 0 of them executable,
                and 0 both writable and executable (the w^x line).";
            attribute :>> parent = "H.MEM.4";
            attribute :>> unit = ("mm::map_kernel", "mm::protect_kernel",
                "mm::clear_root_slots", "early::EarlyMemory::map_window");
        }
        requirement <'L.mm.33'> theImageIsWritableNowhere : ItemLowLevel {
            attribute :>> statement = "No leaf under the kernel's root that maps a
                frame of the image's text or read-only data shall be writable, and the
                direct map shall alias every byte of them read-only.";
            attribute :>> criterion = "The sweep of every leaf under the kernel's root
                finds the image's text and read-only data non-empty, 0 of the leaves
                mapping them writable, and the direct map's leaves over them covering
                every byte (the sealed line).";
            attribute :>> parent = "H.MEM.5";
            attribute :>> unit = ("mm::direct_map", "mm::overlaps_image",
                "vmap::map_device", "early::EarlyMemory::map_window");
        }
        requirement <'L.mm.34'> earlyBootMemoryIsReclaimed : ItemLowLevel {
            attribute :>> statement = "reclaim_boot_memory shall give the frame
                allocator the loader's and the ACPI-reclaimable frames the per-frame
                array covers, above frame 0, and none of the page tables, boot stack or
                boot information the kernel still uses.";
            attribute :>> criterion = "The frames reclaimed equal the loader and
                ACPI-reclaim frames of the memory map inside the array, above frame 0,
                and greater than 0; afterwards no frame of a PageTables, BootStack or
                BootInfo region is free.";
            attribute :>> parent = "H.MEM.14";
            attribute :>> unit = "mm::reclaim_boot_memory";
        }
        requirement <'L.mm.75'> thePstoreRegionIsNeverFree : ItemLowLevel {
            attribute :>> statement = "No frame of a Pstore region shall be free at
                boot, reclaimed, or on a free list.";
            attribute :>> criterion = "After reclaim_boot_memory, every frame of the
                attached region (257 for the 1 MiB ring and its header) reads
                Reserved from the frame allocator, or lies outside its array: none
                Free, FreeTail, Allocated or AllocatedTail, on every boot that
                attached one.";
            attribute :>> parent = "H.MEM.14";
            attribute :>> unit = "mm::reclaim_boot_memory";
        }
        requirement <'L.mm.91'> aRetiredFrameIsNeverAllocatedAgain : ItemLowLevel {
            doc /* docs/MACHINE-CHECK.md §3.4: retirement by late kill; the
                insert, the claim and the free paths' test are under the frame
                allocator's lock (the consultant's M4). */
            attribute :>> statement = "retire_frame shall, in one hold of the
                frame allocator's lock, record the frame and take it off the free
                lists if it is free; release_frame and deallocate_frames shall,
                under that lock, keep a recorded frame allocated and charged to
                nobody instead of freeing it, freeing the rest of a block that
                holds one frame by frame; and a frame the allocator does not
                cover shall not be recorded.";
            attribute :>> criterion = "Stage 2: a frame retired while shared stays
                allocated after both releases and cannot be claimed; one retired
                inside a two-frame block stays allocated when the block is freed
                and its neighbour is free; one retired while free is allocated at
                once; a second retirement answers already. Negative control: the
                free paths' test removed, stage 2 stops. test-mce-driver: a pinned retired
                frame is still listed after quarantine_release; its keep is stage
                2's check (control: the keep removed, stage 2 stops)";
            attribute :>> parent = "H.FAIL.8";
            attribute :>> unit = ("mm::retire_frame",
                "mm::holds_retired",
                "mm::keep_retired",
                "mm::is_retired",
                "mm::release_frame",
                "mm::deallocate_frames",
                "mm::retired_frames");
        }
        requirement <'L.mm.92'> theRetiredSetRefusesWhenFull : ItemLowLevel {
            attribute :>> statement = "Once 256 frames are retired, retire_frame
                shall record no further frame and change nothing, answering full,
                and shall print the set's fullness once.";
            attribute :>> criterion = "Stage 2, the set's room lowered to what the
                check has used: a further frame is refused twice and not retired,
                and the line was printed; the room and the line are given back.";
            attribute :>> parent = "H.FAIL.8";
            attribute :>> unit = ("mm::retire_frame");
        }
        // docs/HEAP-CACHES.md: each processor's cache of free heap objects in
        // front of the heap's lock (the consultant's OK IF 1-10, ledger 4914).
        requirement <'L.mm.93'> anAllocationIsServedByItsProcessorsCache : ItemLowLevel {
            attribute :>> statement = "An allocation of a size class shall take an
                object its processor's cache holds without the heap's lock, and an
                empty cache shall refill REFILL objects of the class under one hold of
                it.";
            attribute :>> criterion = "On one processor with its 2 KiB cache drained,
                the first allocation raises the heap's count by exactly REFILL objects
                and the next REFILL - 1 do not move it.";
            attribute :>> parent = "H.MEM.11";
            attribute :>> unit = ("mm::allocate_through_caches", "mm::with_cache");
        }
        requirement <'L.mm.94'> aFreeGoesToItsProcessorsCache : ItemLowLevel {
            attribute :>> statement = "A free of a size class shall go to its
                processor's cache while the cache has room; a full cache shall give
                back REFILL of its objects and the freed one under one hold of the
                heap's lock.";
            attribute :>> criterion = "REFILL frees into an empty 2 KiB cache leave
                the heap's count unchanged and the cache holding REFILL; with the
                cache full, one more free lowers the count by exactly REFILL + 1
                objects and leaves CACHE_DEPTH - REFILL held.";
            attribute :>> parent = "H.MEM.9";
            attribute :>> unit = "mm::KernelAllocator::dealloc";
        }
        requirement <'L.mm.95'> aRefusalDrainsTheCachesFirst : ItemLowLevel {
            attribute :>> statement = "Every refusal of the heap -- a refill, a large
                request, a reserve's fill -- shall drain every processor's cache and
                try once more before it refuses; a reserved section then draws on its
                reserve as before.";
            attribute :>> criterion = "With every free frame held and this
                processor's cache holding 2 KiB objects made one after another, whole
                pages of them, an allocation of one page is served, and the cached
                bytes have fallen; so is a reserved section whose fill needs one 2 KiB
                object, every free one of that class taken from the heap, and one
                that holds a page, each with the cached bytes fallen and the reserve
                full after it.";
            attribute :>> parent = "H.MEM.11";
            attribute :>> unit = ("mm::heap_or_drain", "mm::reserve::enter");
        }
        requirement <'L.mm.96'> theHeapCountLeavesTheCachesOut : ItemLowLevel {
            attribute :>> statement = "heap_allocated() and the held-memory window's
                heap bytes shall be the heap's allocated bytes less the bytes the
                processors' caches hold.";
            attribute :>> criterion = "With a 2 KiB cache full, heap_allocated() is
                the heap's own count less the cached bytes, and the cached bytes are
                at least CACHE_DEPTH objects.";
            attribute :>> parent = "H.MEM.9";
            attribute :>> unit = "mm::heap_allocated";
        }
        requirement <'L.mm.97'> theDrainEmptiesEveryCache : ItemLowLevel {
            attribute :>> statement = "The drain shall give every processor's cached
                objects back to the heap, taking one cache lock at a time, and shall
                stop the machine (FX-0012) when entered with this processor's cache
                lock held.";
            attribute :>> criterion = "After a drain this processor's cache holds
                nothing and the heap's count is where it was before the objects were
                cached; every processor allocating, freeing across processors and
                draining at once finishes within 20 s with no allocation refused, every
                object they made freed and the caches empty after a drain.";
            attribute :>> parent = "H.MEM.9";
            attribute :>> unit = "mm::drain_caches";
        }
        requirement <'L.mm.98'> anInjectedRefusalIsNotRetried : ItemLowLevel {
            attribute :>> statement = "A refusal the failure injection made shall be
                answered without a drain or a retry.";
            attribute :>> criterion = "With warm caches, an injection refusing the
                next frame makes the next allocation of one page return null, and the
                injection counts exactly one failure.";
            attribute :>> parent = "H.MEM.11";
            attribute :>> unit = ("mm::heap_or_drain", "fallible::injected_failures");
        }
        // docs/BTRFS-PRESSURE.md, "The transaction aborted out of memory" (2026-11-08).
        requirement <'L.mm.136'> aRefusedHeapAllocationReclaims : ItemLowLevel {
            attribute :>> statement = "A heap allocation the heap refused after the drain shall,
                where it may block, reclaim clean cache and try again while a reclaim gives some
                back, at most eight times; not where it may not block, not inside a reclaim, and
                not for a refusal the failure injection made.";
            attribute :>> criterion = "The page cache's self-check with kernel objects alone
                (user::rehome_cache_check, check_a_refused_heap_allocation_reclaims): with a
                512-page cached file of the check's own source and every free frame held, a
                page of heap is served and the count of refused allocations a reclaim let in
                grows, in at most three tries. Control: heap_or_reclaim answering None at
                once -- the boot stops on the check's 'was not served after a reclaim'. Not in
                interrupt service (check_no_heap_reclaim_in_interrupt_service): heap_may_reclaim
                answers yes in the check's task, with interrupts on and nothing held, and no for
                the same task inside irq::serviced, where only its interrupt test can say no.
                Control: the interrupt test removed -- the boot stops on 'the kernel heap may
                reclaim or kill inside interrupt service' (f107-irq-c1).";
            attribute :>> parent = "H.MEM.11";
            attribute :>> unit = ("mm::heap_or_reclaim", "mm::heap_may_reclaim",
                "mm::injection_refused", "mm::reclaim_for_kernel");
        }
        requirement <'L.mm.137'> theKernelsHeadroomIsRefilled : ItemLowLevel {
            attribute :>> statement = "When a kernel frame leaves fewer than half the watermark
                free, each later heap allocation that may block shall make one reclaim of a
                fill's run and what the free count lacks of the watermark, one task at a time,
                none within 10 ms after one that gave nothing back, until a kernel frame or a
                reclaim leaves at least half the watermark free.";
            attribute :>> criterion = "test-btrfs-pressure's commit boot: on a 768 MiB machine
                whose memory the page cache holds, 24576 names made by the shell alone through a
                writable btrfs are all made and every 64th found again, the sync succeeds, a file
                committed before them reads back whole, and the kernel never says that a
                transaction was aborted. Control: refill_headroom returning at once -- FX-0008,
                memory allocation of N bytes failed (204 and 16384 seen), and the guest never
                says done.";
            attribute :>> parent = "H.MEM.11";
            attribute :>> unit = ("mm::refill_headroom", "mm::note_headroom");
        }
        // docs/BTRFS-PRESSURE.md, "No clean cache left: the kill for the kernel's heap" (2026-11-08).
        requirement <'L.mm.138'> theKernelsHeapIsGivenRoomByAKill : ItemLowLevel {
            attribute :>> statement = "A heap allocation that may block, refused after the drain
                and after its reclaims (L.mm.136), with fewer frames free than the watermark, shall
                ask the machine-wide OOM kill -- the live process with the most resident pages,
                never pid 1, never a kernel task, a victim still ending waited for, none within
                250 ms of the last machine-wide kill and none while the space of the last process
                killed for the heap is held and the kill still waits for it, neither emptied by
                the emptier nor given up (L.object.375), the kill itself emptying nothing where it
                is asked (L.object.374) -- and try the heap again while the kill answers
                retry and the free count stays under the watermark, at most 1024 answers. It shall
                fail when the allocating process is the one chosen or is ending, when nothing can
                be killed, and when no list of the live processes can be made. Not for a refusal
                the failure injection made, and what the kill itself allocates is never answered
                by a reclaim or a kill; the heap's refusal of it is answered by the reserve as
                L.mm.139 says. A reservation's growth for a heap scope (mm::reservation_grow)
                still refused after its reclaims (L.mm.146), for want of free frames over the
                watermark, the outstanding promise and the growth, shall ask the same kill and
                try the growth again on the same terms: so with up to the growth free above the
                watermark, unlike Linux, which kills only once an allocation failed (ledger 8544
                O1; MEMORY-AND-TIMING 2.2am).";
            attribute :>> criterion = "test-btrfs-pressure's hog boot: on a 768 MiB machine a
                program holds all of MemAvailable but 16 MiB as anonymous memory, then 24576 names
                made by the shell alone through a writable btrfs are all made and every 64th found
                again, the sync succeeds, a file committed before them reads back whole, the
                kernel never says that a transaction was aborted, and it says exactly once that it
                killed a process for its heap; the floor, evict and commit boots say it never.
                Control: heap_or_kill returning None at once and reservation_grow asking no kill
                -- the kernel says a transaction was aborted (out of memory), stops with FX-0008
                on an allocation that cannot report failure, or a create answers ENOMEM, whichever
                the refusal meets first. Never in interrupt service: L.mm.136's case of
                heap_may_reclaim, which the kill's callers ask first (f107-irq-c1);
                check-stack-depth leaves the kill out of a timer's interrupt on that guard
                (INTERRUPT_CANNOT, F-107). The hold's end and the kill's hand-off are
                L.object.375's and L.object.374's cases.";
            attribute :>> parent = "H.MEM.11";
            attribute :>> unit = ("mm::heap_or_kill", "mm::while_killing",
                "object::oom::for_kernel_heap", "object::oom::kernel_victim_held",
                "mm::reservation_grow");
        }
        // docs/BTRFS-PRESSURE.md, "Two refusals the kill could not answer" (2026-11-08,
        // consultant ledger 8172 B2).
        requirement <'L.mm.139'> theHeapKillerDrawsOnTheReserve : ItemLowLevel {
            attribute :>> statement = "An allocation the heap refused, made outside any reserved
                section by the task choosing and killing for the kernel's heap (L.mm.138), or by
                the OOM kill's emptier (L.object.376), outside interrupt context, shall be served
                from that processor's allocation reserve while the reserve holds a block of its
                class; the same allocation by any other task, or in interrupt context, shall stay
                refused.";
            attribute :>> criterion = "The allocation check (mm::check,
                check_the_heap_killer_draws_outside_a_section), preemption off, the reserve
                filled, the heap made to refuse the checking task's allocations: named the heap's
                killer, a 200-byte allocation outside any section is served holding what was put
                in it and the drawn count rises; with no killer named, and with another task
                named, it is refused and the drawn count is unchanged; inside a section, no killer
                named, it is served from the reserve; named the OOM kill's emptier, it is served.
                Controls: the fallback's
                predicate false (the first fails), killing_for_the_heap true for every task (the
                second fails).";
            attribute :>> parent = "H.MEM.11";
            attribute :>> unit = ("object::oom::killing_for_the_heap", "mm::reserve::draw",
                "mm::KernelAllocator::alloc", "mm::reserve::heap_refused_here");
        }
        // docs/BTRFS-PRESSURE.md, "Against Linux's btrfs", W1-a (ledger 8337).
        requirement <'L.mm.140'> aHeapScopeDrawsFromItsReservation : ItemLowLevel {
            attribute :>> statement = "While a task holds a heap scope on a bound reservation,
                its task-context kernel-heap allocations of at most a page shall be served by
                that reservation's heap first, whatever its job's reservation, and by the shared
                heap only past the reservation's room, each such counted; a larger one, a run of
                frames a count of frames cannot promise, as outside the scope and not counted;
                never in interrupt context; not while the scope is suspended; and from the
                guard's drop on as before the scope. A scope is refused in a retyped build, in
                interrupt context, and on a reservation not bound.";
            attribute :>> criterion = "At stage 9 (object::reserve_check, check_the_heap_scope):
                a reservation of 16 frames and a scope on it, the shared heap made to refuse the
                checking task's scoped allocations: an object of each of the eight size classes
                and then 2048-byte objects until one is refused all lie on pages drawn from the
                reservation, no more than 16 frames drawn, the refusal counted; an allocation in
                interrupt context, one with the scope suspended and one after the guard is
                dropped lie on shared pages, one after the suspension on a drawn page, and a
                request of two pages in the scope on shared pages with the count unchanged;
                freed, the reservation's heap holds nothing. Controls: the allocator not reading
                the scope (the first fails), the guard not putting the task's scope back (the
                last fails), a request above a page routed to the scope (the two pages are
                counted).";
            attribute :>> parent = "H.QUOTA.15";
            attribute :>> unit = ("mm::heap_scope", "mm::heap_scope_suspended",
                "mm::HeapScope::drop", "mm::scoped_here", "mm::heap_entry",
                "mm::scope_overrun", "mm::note_scope_overrun", "mm::shared_refused_here",
                "mm::KernelAllocator::alloc");
        }
        // docs/BTRFS-PRESSURE.md, "Against Linux's btrfs", W1-c (ledger 8337 W1.8).
        requirement <'L.mm.146'> aRefusedReservationGrowthReclaims : ItemLowLevel {
            attribute :>> statement = "A reservation's growth for a heap scope
                (mm::reservation_grow), refused for want of free frames, shall, where it may
                block, reclaim clean cache and try the growth again while a reclaim gives some
                back, at most eight times, with the scope suspended for the reclaim's own
                allocations, and before its first kill purge the large-request area's kept
                frames once and try the growth again (L.mm.143); not where it may not block and
                not under the failure injection; a refusal for an entry not bound stands at
                once.";
            attribute :>> criterion = "The page cache's self-check with kernel objects alone
                (user::rehome_cache_check, check_a_refused_reservation_growth_reclaims): with a
                512-page cached file of the check's own source and the free count held one
                under what a growth of 16 frames needs, the resize alone is refused, the growth
                is admitted, and the count of growths a reclaim let in grows, in at most three
                tries. Control: reservation_grow's reclaims removed -- the boot stops on the
                check's 'was not admitted after a reclaim'.";
            attribute :>> parent = "H.MEM.11";
            attribute :>> unit = ("mm::reservation_grow", "mm::reclaim_for_kernel");
        }
        // docs/HEAP-SLAB-GIVE-BACK.md (ledger 9543, 9574, 9628 SG.2):
        // design (d)'s D1, an emptied slab page given back without a walk.
        requirement <'L.mm.147'> aGiveBackReadsItsPageNotTheList : ItemLowLevel {
            attribute :>> statement = "A free that empties a slab page shall take that
                page's objects off its class's free list in at most 6 link accesses for each
                object one page of its class holds, whatever the length of that list.";
            attribute :>> criterion = "A link access is one Backing::read_link or
                Backing::write_link call (ferrix_heap::UNLINK_ACCESSES, 6: an object's own two
                links read, its two neighbours' links that name it read and verified, up to
                two writes). ferrix-heap's host test a_give_back_reads_a_page_not_the_list: 400
                pages of the 16-byte class emptied, 102,400 objects, with at least 51,000
                others on the list at each emptying; each emptying free within 6 x 256 + 3
                accesses, and the list then holds exactly the free objects of the pages still
                held. Control: the class-list walk put back in unlink_page, the test FAILED.
                The stage 2 boot check (mm::check::give_back_case, 160,000 objects made, 200
                pages kept partly in use, 400 emptied, on the shared heap) and the
                reservation check's case on a reserved job's heap (10,240 objects, 32 pages
                emptied): the heap's give-back counts at most 6 accesses an object, a count
                and never a time. Control: the walk put back -- the boot stops on 'a heap
                give-back made more link accesses than its page's objects allow'. With checks
                on, a neighbour that does not name the object makes the heap stop through
                Backing::links_disagree before any write, at an unlink and at a pop
                (a_double_free_into_a_page_stops_its_give_back,
                an_overwritten_link_stops_its_give_back, an_overwritten_previous_stops_a_pop;
                controls: the verification taken out, the tests FAILED), and the kernel
                answers with FX-0013, 'a kernel heap free list's links disagree' (control: a
                free object's link written over inside the boot case, the boot stops with
                it).";
            attribute :>> parent = "H.MEM.9";
            // The give-back itself is ferrix-heap's (Heap::deallocate,
            // Heap::unlink_page, Heap::unlink_one), a crate the manifest does
            // not list as a member (F-76), so its functions cannot be units
            // here, as L.user.245's sort cannot (F-56): they are named in the
            // criterion, and the kernel's glue that serves and stops it is.
            attribute :>> unit = ("mm::KernelAllocator::dealloc",
                "mm::KernelPages::links_disagree", "mm::ReservedPages::links_disagree");
        }
        // docs/ROBUSTNESS.md §2.6, R6 (ledger 8481, 8503).
        requirement <'L.mm.141'> aLargeRequestNeedsNoRun : ItemLowLevel {
            attribute :>> statement = "A kernel heap request above a page and at most
                2^MAX_ORDER pages, aligned to at most a page, that the buddy refuses as one run
                shall be served from single frames mapped into the large-request area, in this
                order: the reservation's heap (the job's, or a heap scope's for a request of at
                most a page, so in practice the job's, L.mm.140), then the area from frames
                drawn from that reservation, then on an architecture whose invalidation is local
                one purge and both again where the caller may block, then the scope's overrun
                counted once, then the shared heap, then the area from the kernel's frames, then
                after each reclaim and each kill the shared heap and the area from the kernel's
                frames, and the reserve last; the area tried only where the shared heap is
                (the same refusal decision), and never in a retyped build. A request the buddy
                serves is served as before.";
            attribute :>> criterion = "At stage 9 (mm::large_check), with the buddy made to
                refuse the checking task's runs: a 32 KiB request by a task of a job with a
                reservation is served from the area, its 8 pages drawn from that reservation,
                the page above it not mapped; a 128 KiB request with no reservation is served
                from the area; 4 MiB with interrupts masked is served. Control: the large path
                removed from the allocator (the 32 KiB request fails); the large path taking
                the kernel's frames for a reservation's draw (its frame is not drawn from the
                reservation).";
            attribute :>> parent = "H.MEM.11";
            attribute :>> unit = ("mm::KernelAllocator::alloc", "mm::drawn_attempt",
                "mm::shared_attempt", "mm::from_shared_heap", "mm::heap_or_reclaim",
                "mm::heap_or_kill", "mm::large::allocate", "mm::large::pages_for",
                "mm::large::take_block", "mm::large::init", "mm::take_frames",
                "mm::runs_refused_here");
        }
        requirement <'L.mm.142'> aLargeBlockIsFreedByTheArea : ItemLowLevel {
            attribute :>> statement = "The free of an address in the kernel's dynamic space
                shall be routed to the large-request area before any heap's tag is read; each
                frame of a freed block shall go back to the reservation its tag names; an
                address outside the area, or one that is not the base of a live block of the
                request's order, shall be counted and change nothing: the test made under the
                area's lock before any leaf is cleared.";
            attribute :>> criterion = "At stage 9 the scope's 32 KiB block, freed and purged,
                leaves the reservation's drawn count where it was before the request; a free of
                a dynamic-space address outside the area, and one of an address inside a live
                block that is not its base, are each counted, and the mapping and the block
                they name still translate to their frames; no other such free is counted.
                Controls: dealloc's area recognition removed (the block does not wait on the
                lazy list); the ownership test removed (the free outside the area clears a
                mapping it does not own).";
            attribute :>> parent = ("H.MEM.9", "H.QUOTA.15");
            attribute :>> unit = ("mm::KernelAllocator::dealloc", "mm::large::in_dynamic_space",
                "mm::large::free", "mm::large::owns", "mm::large::release_pages");
        }
        requirement <'L.mm.143'> aLargeFreeWaitsForItsShootdown : ItemLowLevel {
            attribute :>> statement = "A freed large block's addresses shall not be handed out
                again, and on an architecture whose TLB invalidation is local its frames shall
                not go back to the frame allocator, before one shootdown that covers them has
                returned; neither a free nor a reservation's unbind shall begin a shootdown,
                wherever it is made; the lazy list shall be purged, only where the caller may
                block, by an allocation that finds a purge wanted or no address space, and
                besides by the reaper, which a free past the list's threshold asks for, and a
                reservation's unbind while frames are kept (the purges before a draw is
                counted short, a reclaim's failure, a kill or a floor's refusal are L.mm.141's,
                L.mm.146's and the kill's own, through mm::large::purge_held); the kept
                frames' chain shall be checked link by link, and a bad link
                counted and its rest kept, never freed. Between a free and the purge, on an
                architecture whose invalidation is local, another processor may still translate
                the freed address; neither the address nor its frame is anyone's meanwhile
                (finding F-108).";
            attribute :>> criterion = "At stage 9 a scoped 32 KiB block freed with interrupts
                masked begins no purge, waits on the lazy list, and on x86-64 keeps its frames
                drawn; a purge in task context empties the list and gives them back; frees past
                a lowered threshold made masked ask for a purge, which the reaper makes within
                2 s (the count of purges past its value before the masked part, and the flag, seen set inside it, clear again: only a purge's start clears it), and a masked request that finds that purge wanted begins none (a masked
                round in which the machine's count of purges moved, or the flag cleared, is
                made again, up to three rounds: another processor's purge can fall inside
                one, a purge begun here falls inside each, and the stage line says how many
                were made and why); an entry
                bound and unbound masked after a masked free under the threshold
                begins no purge, and asks for one on x86-64, where the free's frames are kept,
                and for none on the Arm pair, where none are; over 64 rounds of a 32 KiB
                block made and freed in task context with the threshold lowered to 16 units,
                the lazy list never holds more than the threshold and one block; bad links 0.
                Host: a detached
                block is not handed out until it is given back (ferrix-frame, large_area::
                a_freed_block_is_not_handed_out_until_the_purge_gives_it_back). By analysis:
                check-stack-depth finds no way from a task's last drop to a shootdown on any
                of the three architectures, by direct calls, x86-64's calls through the GOT and
                through a register loaded from it, and ARMv7-A's calls with their immediate
                (F-110); each walk reaches the heap's free from that drop; the units are one
                source for the three.
                Controls: a purge allowed where the caller may not block (the boot stops on 'a
                shootdown was requested with interrupts masked'); a retired block given back
                at once (host: that test FAILED); x86-64 frames freed at the free ('a masked
                free gave its frames back before their shootdown'); a free past the threshold
                that purges where it may block, and an unbind that purges where it may block
                (check-stack-depth, each: 'a task's last drop reaches' smp::
                flush_tlb_everywhere by way of mm::large::purge); an unbind that asks for
                nothing ('a reservation's unbind while frames were kept did not ask the reaper
                for a purge'); an allocation that makes no purge for one wanted ('frees past
                the lazy threshold in task context were not purged by the next allocation').";
            attribute :>> parent = ("H.MEM.17", "H.MEM.12");
            attribute :>> unit = ("mm::large::retire", "mm::large::purge",
                "mm::large::purge_held", "mm::large::ask_purge_held", "mm::large::take_block",
                "mm::large::give_back_kept", "mm::large::link", "mm::large::next_of",
                "mm::large::counts", "mm::reservation_unbind",
                "sched::leftovers::nudge", "sched::leftovers::wanted",
                "sched::leftovers::reaper");
        }
        requirement <'L.mm.144'> aLargeMappingAllocatesNothing : ItemLowLevel {
            attribute :>> statement = "Mapping a large block shall allocate nothing: every
                page-level table of the 2 MiB-aligned area made at boot, never pruned or freed,
                a leaf written only by its block's owner, by a store a walker never sees half
                of; a full area shall answer a refusal; a request refused part way shall keep
                no frame and put its block on the lazy list; a leaf found present at a map or
                absent at a free shall be counted and never served.";
            attribute :>> criterion = "At stage 9 every page-level table of the area is still
                linked at the check's end (populate over the whole area through memory that
                gives no table succeeds: the R6F.3 check), and the two-owner count is 0. Host: a populated range maps through memory that gives no
                table, a range with none answers OutOfMemory and writes nothing, and an unmap
                beside a populated range gives back none of its tables (ferrix-paging).";
            attribute :>> parent = ("H.MEM.11", "H.MEM.9");
            attribute :>> unit = ("mm::large::AreaTables::write", "mm::large::AreaTables::allocate_table",
                "mm::large::store_word",
                "mm::large::mapper", "mm::large::area_bytes", "mm::large::side_array",
                "vmap::set_aside", "vmap::insert_span");
        }
        requirement <'L.mm.145'> aLargeRequestIsServedInEveryContext : ItemLowLevel {
            attribute :>> statement = "The large path shall serve an allocation and a free in
                every context -- an interrupt, interrupts masked, a spin lock or TABLES held --
                taking only the area's lock and the frame allocator's, never nested and never
                TABLES or HEAP; it shall purge only where the caller may block, one purge at a
                time; an interrupt's request shall take the kernel's frames only.";
            attribute :>> criterion = "At stage 9 a 32 KiB request made and freed inside a
                with_tables body is served from the area, and the 4 MiB request is served and
                freed with interrupts masked.";
            attribute :>> parent = "H.MEM.11";
            attribute :>> unit = ("mm::large::with_area", "arch::x86_64::publish_tables",
                "arch::aarch64::publish_tables", "arch::armv7a::publish_tables");
        }
        // docs/RAM-RELEASE.md §2, R1 (consultant ledger 4971, 5022).
        requirement <'L.mm.99'> theArchivesPagesComeBack : ItemLowLevel {
            attribute :>> statement = "Once the root is final, at most once a boot, the
                frames the initramfs archive fills whole and the frame allocator
                describes shall be given to it, in batches of at most 1024 frames a
                hold, and MemTotal and the watermark shall be computed from the
                frames managed after.";
            attribute :>> criterion = "On every boot whose checks run, the frames
                managed grow by exactly the archive's whole pages inside the frame
                array, none of them is Reserved after, and the watermark is
                watermark_for of the new count, in one hold per aligned batch of
                1024 frames it touches and no more than 1024 frames a hold; and
                whole_frames counts an archive unaligned at both ends, an aligned
                one, one the frame array ends inside, one at frame 0 and one
                filling no page whole as inward and inside the array (the
                `release  checked` line). No release, the watermark left as it
                was, or the first page rounded down stops the boot there.";
            attribute :>> parent = "H.MEM.9";
            attribute :>> unit = ("mm::give_back_initrd", "mm::initrd_frames",
                "mm::whole_frames");
        }
        requirement <'L.mm.100'> noReaderOutlivesTheArchive : ItemLowLevel {
            attribute :>> statement = "The initramfs archive shall be kept only when it
                lies in one Initrd region inside the direct map, read only under
                its lock, lent to a closure whose answer cannot borrow it, and
                give_back_initrd shall take it out under that lock before any of its
                frames is given away; after that it shall answer nothing.";
            attribute :>> criterion = "After the release with_initrd and initrd_span
                answer None on every boot whose checks run, and initrd_readable
                takes an archive unaligned at both ends inside an Initrd region and
                refuses one across the region's end, one in a region of another
                kind or in none, and one past the direct map (the `release
                checked` line). A release that leaves the archive kept, or a range
                test that takes every range, stops the boot there.";
            attribute :>> parent = "H.MEM.9";
            attribute :>> unit = ("mm::keep_initrd", "mm::initrd_readable", "mm::with_initrd",
                "mm::give_back_initrd");
        }
        requirement <'L.mm.101'> aScrubClaimLeavesEveryOrder : ItemLowLevel {
            attribute :>> statement = "The scrubber shall claim a frame only in one hold of the frame
                allocator's lock in which the frame is free, not retired, free
                memory is at least twice the watermark, and another free block
                of the claimed block's order or larger exists; otherwise it
                shall skip the frame, and stop the batch at the watermark.";
            attribute :>> criterion = "ferrix-frame's host test
                a_claim_leaves_another_block_of_its_order; check_scrubber: a
                frame the check holds is skipped, its contents untouched, and
                a clean frame's batch leaves the free count and every order's
                free-block count as they were. Control: the claim's free test
                removed -- the held frame changes.";
            attribute :>> parent = "H.FAIL.9";
            attribute :>> unit = ("mm::scrub::claim", "mm::scrub::run", "mm::scrub::test_batch");
        }
        requirement <'L.mm.102'> aScrubbedFrameGoesBackUncounted : ItemLowLevel {
            attribute :>> statement = "A frame the scrubber found good shall be zeroed and freed
                through the path that keeps a retired frame held, moving none
                of the allocator's counters, as its claim moved none.";
            attribute :>> criterion = "check_scrubber: the free count and the free-block counts after
                a clean frame's batch equal those before.";
            attribute :>> parent = "H.FAIL.9";
            attribute :>> unit = ("mm::scrub::release", "mm::scrub::zero");
        }
        requirement <'L.mm.103'> fourPatternsEachReadBack : ItemLowLevel {
            attribute :>> statement = "Each test shall write the frame four times -- 0x5555..,
                0xAAAA.., each word its physical address, and that inverted --
                each with writes that read nothing, evict it to the point of
                coherency, and read every word back and compare; it shall read
                no line whose memory contents it has not itself written in the
                current pass.";
            attribute :>> criterion = "test-scrub: a full sweep of good memory finds nothing bad;
                check_scrubber's injected failure is seen on a read-back; the
                arch requirements L.x86_64.243, L.aarch64.68 and L.armv7a.29
                for the writes and the eviction.";
            attribute :>> parent = "H.FAIL.9";
            attribute :>> unit = ("mm::scrub::test", "mm::scrub::injected");
        }
        requirement <'L.mm.104'> aFrameIsBadOnlyAfterItsRetest : ItemLowLevel {
            attribute :>> statement = "A frame that fails a test shall be tested again at once; it is
                bad if the retest fails or if it failed before as one of the
                last 64 suspects; one that passes its retest shall be
                remembered as a suspect and released.";
            attribute :>> criterion = "check_scrubber: an injected one-off makes a suspect, released;
                the same frame failing again later is retired; an injected
                stuck bit is retired after its retest. Control: retirement
                after one failure -- the one-off retires a good frame.";
            attribute :>> parent = "H.FAIL.9";
            attribute :>> unit = ("mm::scrub::judge", "mm::scrub::was_suspect", "mm::scrub::remember_suspect");
        }
        requirement <'L.mm.105'> aBadFrameIsKeptAndTheShareHeld : ItemLowLevel {
            attribute :>> statement = "A bad frame shall be retired and freed through the
                retired-frame decision, so that it stays allocated, owned by
                nobody and retired; where the retired set is full or the
                scrubber's share of 192 used, it shall be held claimed, not
                released, and the batch shall stop, so that at most one frame
                is held out.";
            attribute :>> criterion = "check_scrubber: the retired frames are allocated, owned by
                nobody and in the set; with the set full a bad frame is held
                out and the batch stops after it. Control: a bad frame
                released when the set is full.";
            attribute :>> parent = "H.FAIL.9";
            attribute :>> unit = ("mm::scrub::keep_bad", "mm::scrub::share_used");
        }
        requirement <'L.mm.106'> theScrubberStandsDownWhereItMust : ItemLowLevel {
            attribute :>> statement = "At boot the kernel shall decide once, from SMBIOS type 16's
                system memory arrays, whether the scrubber runs: where every
                array says None; and where they say Other or Unknown or none
                exists only if the processor writes without reading; never
                where one says Parity, ECC or CRC or a type 16 cannot be read,
                nor as a guest (or where AArch64 firmware names no PSCI
                conduit); the gate's override, test-only and refused in a
                certified profile's command line, is honoured only where a
                hypervisor is positively seen (x86-64's hypervisor bit,
                AArch64's hvc conduit or /hypervisor node).";
            attribute :>> criterion = "ferrix-smbios's host test
                the_memory_arrays_say_whether_memory_corrects; test-scrub: the
                boot without the override stands down for QEMU's multi-bit
                ECC, the override taken under QEMU's hypervisor, ARMv7-A's
                stand-down. Control: the type-16 stand-down removed -- the
                boot without the override runs.";
            attribute :>> parent = "H.FAIL.9";
            attribute :>> unit = ("mm::scrub::decide", "mm::scrub::verdict", "mm::scrub::standing", "mm::scrub::override_asked", "mm::scrub::Standing::reason", "mm::scrub::Standing::from_number");
        }
        requirement <'L.mm.107'> theScrubbersCountsShowCoverage : ItemLowLevel {
            attribute :>> statement = "/proc/ferrix-scrub, readable by all, shall give the frames
                managed, the frames tested in all and this sweep, the sweeps,
                the suspects, bad, retired and held counts, and the standing
                with its reason, and no address.";
            attribute :>> criterion = "test-scrub: the guest reads tested against managed after a
                sweep and the standing in both boots.";
            attribute :>> parent = "H.FAIL.9";
            attribute :>> unit = ("mm::scrub::render");
        }
        requirement <'L.mm.109'> aRetirementIsRecordedForTheNextBoot : ItemLowLevel {
            doc /* docs/MACHINE-CHECK-RESTART.md §2.3. */
            attribute :>> statement = "retire_frame shall record each frame it newly retires --
                Claimed or Marked, never Already or Full -- in the pstore bad-frame
                table, a slot claimed by one fetch_add and the entry stored and
                written back after the claim, past 64 said once; and no boot check's
                retirement shall reach the live table.";
            attribute :>> criterion = "Stage 2's check_kept_out: the checked retirements leave
                the live table's count as it was; test-mce-restart: boot 2's loader
                keeps the page out from the table. Negative control: the table write
                removed, the judge fails.";
            attribute :>> parent = "H.FAIL.12";
            attribute :>> unit = ("mm::retire_frame", "mm::table_held", "mm::hold_table");
        }
        requirement <'L.mm.110'> badFramesAreLeftOut : ItemLowLevel {
            doc /* docs/MACHINE-CHECK-RESTART.md §2.8. */
            attribute :>> statement = "The frame allocator shall give no BadFrame page to its
                free lists, shall enter each in the retired set before the first
                allocation and say how many, and the pstore attach shall write each
                into the new table again; retire_frame shall answer Already for such
                a frame before NotCovered.";
            attribute :>> criterion = "Stage 2's check_kept_out: a frame the allocator does not
                manage, entered as init enters a BadFrame page, answers Already;
                test-mce-restart: boot 2 says 1 frames left out as bad and its poll
                finds the frame already retired; boots after it keep it out from the
                rewritten table. Negative control: the leave-out removed, the gate
                fails.";
            attribute :>> parent = "H.FAIL.12";
            attribute :>> unit = ("mm::keep_out", "mm::init", "console::pstore::attach");
        }
        requirement <'L.mm.108'> oneBatchAtATime : ItemLowLevel {
            attribute :>> statement = "Only one batch shall run at a time machine-wide, of at most 64
                frames; a batch asked for while one runs shall be refused, and
                a budget of 0 or past 64 refused, with nothing tested.";
            attribute :>> criterion = "The native boot check: a budget of 0 and of 65 refused
                INVALID_ARGS; test-scrub's memscrub batches answered.";
            attribute :>> parent = "H.FAIL.9";
            attribute :>> unit = ("mm::scrub::test_batch", "mm::scrub::batch_for_check");
        }
        // Restated by docs/RAM-RELEASE.md R1 (consultant ledger 5022, condition 1):
        // the archive's release sets it a second time.
        requirement <'L.mm.71'> theWatermarkIsSizedOnce : ItemLowLevel {
            attribute :>> statement = "init shall set the watermark to the frames the
                allocator manages divided by 128, and no fewer than 256 frames nor
                more than 8192; give_back_initrd shall set it once more, the same
                way, from the frames managed after the initramfs's release, in the
                hold of the frame allocator that inserts the release's last frames.";
            attribute :>> criterion = "The watermark equals watermark_for of the
                frames managed at init, and watermark_for gives 256 for 0 frames,
                300 for 38400 and 8192 for the largest count (the `watermark`
                line); after the release it equals watermark_for of the frames
                managed then (the `release` line).";
            attribute :>> parent = "H.QUOTA.13";
            attribute :>> unit = ("mm::init", "mm::watermark_for", "mm::watermark",
                "mm::give_back_initrd");
        }
        requirement <'L.mm.72'> aProgramsFramesStopAtTheWatermark : ItemLowLevel {
            attribute :>> statement = "allocate_user_frame and allocate_user_run
                shall refuse frames that would leave fewer than the watermark free,
                deciding in the same hold of the frame allocator's lock as the
                frames are taken, and a refusal shall take back any charge made for
                them.";
            attribute :>> criterion = "At stage 2, with no job charged, single
                frames taken until refused leave exactly the watermark free; a run
                of two is given at two above it and refused at one above it while a
                block of two is free; a single frame is given at one above it.";
            attribute :>> parent = "H.QUOTA.13";
            attribute :>> unit = ("mm::allocate_program_frames",
                "mm::allocate_user_frame", "mm::allocate_user_run");
        }
        requirement <'L.mm.73'> aProgramsTablesStopAtTheWatermark : ItemLowLevel {
            attribute :>> statement = "A page table for a user mapping shall be
                taken as a program's frame, refused at the watermark whether or not
                its job has a quota slot, and zeroed before it is used.";
            attribute :>> criterion = "At stage 2, with exactly the watermark free,
                a program's page table with no job to charge is refused; with one
                frame more it is given, and the free count is the watermark again.";
            attribute :>> parent = "H.QUOTA.13";
            attribute :>> unit = ("mm::ChargedTables::allocate_table", "mm::map_in");
        }
        requirement <'L.mm.74'> theKernelIsServedBelowTheWatermark : ItemLowLevel {
            attribute :>> statement = "allocate_frames and the heap's page supply
                shall not be refused by the watermark.";
            attribute :>> criterion = "At stage 2, with exactly the watermark free,
                a kernel frame is given, and then a 16 KiB heap allocation takes a
                fresh page; both are given back and the frame window closes on the
                count it opened at.";
            attribute :>> parent = "H.QUOTA.13";
            attribute :>> unit = ("mm::allocate_frames", "mm::KernelPages::allocate_pages");
        }
    }

    package Reservations {
        doc /* src/kernel/src/mm/reservation.rs: frames the kernel promises a
             * job (K12, docs/microkernel/K12.md). F stands for the free
             * frames, W for the watermark and O for the outstanding promise,
             * the sum over the reservations of size less drawn. */

        requirement <'L.mm.76'> aReservationIsAdmittedUnderTheLock : ItemLowLevel {
            attribute :>> statement = "A reservation's growth by d frames of
                promise shall be admitted in one hold of the frame allocator's
                lock only if F - d >= W + O, raising O by d; a refusal shall
                answer the shortfall and change nothing; a shrink, to below what
                is drawn as well, shall always be admitted, whatever F.";
            attribute :>> criterion = "At stage 2 a reservation of F - W - O + 1
                frames is refused with O unchanged, and one of 64 frames raises O
                by exactly 64; with the free count at O, under W + O, and all 64
                frames drawn, a shrink to 63 and back to 64 is admitted with O
                unchanged.";
            attribute :>> parent = "H.QUOTA.16";
            attribute :>> unit = ("mm::reservation::resize", "mm::reservation_resize",
                "mm::reservation::bind", "mm::reservation_bind");
        }
        requirement <'L.mm.77'> aProgramStopsAtThePromise : ItemLowLevel {
            attribute :>> statement = "A frame, run or page table of a program's
                not drawn from a reservation shall be refused when taking its n
                frames would leave F - n < W + O.";
            attribute :>> criterion = "At stage 2, with 64 frames promised,
                program frames taken until refused leave exactly W + 64 free, by each
                of the rule's two sites: the plain path's inline floor, and take's
                arm for a reservation without room, a frame through the reservation's
                ledger taking no promised frame.";
            attribute :>> parent = "H.QUOTA.15";
            attribute :>> unit = ("mm::reservation::take", "mm::take_frames",
                "mm::allocate_program_frames", "mm::program_floor");
        }
        requirement <'L.mm.78'> theKernelStopsAtThePromise : ItemLowLevel {
            attribute :>> statement = "allocate_frames, allocate_frame_run and the
                heap's page supply shall be refused when taking n frames would
                leave F - n < O.";
            attribute :>> criterion = "At stage 2, with 64 frames promised and the
                programs stopped, kernel frames taken until refused leave
                exactly 64 free.";
            attribute :>> parent = "H.QUOTA.15";
            attribute :>> unit = ("mm::allocate_frames", "mm::allocate_frame_run",
                "mm::reservation::take");
        }
        requirement <'L.mm.79'> aReservationsFramesAreDrawn : ItemLowLevel {
            attribute :>> statement = "A program's frames for a job whose
                reservation is bound and has drawn + n <= size, in task context,
                shall be given while n frames are free, tagged with the
                reservation, drawn raised by n and O lowered by n, in the hold
                that takes them; in interrupt context none shall be drawn.";
            attribute :>> criterion = "At stage 2, below both floors, 64 frames
                drawn from a 64-frame reservation are each given and tagged, O
                falling one for one to 0, and the 65th is refused; at stage 9 a
                reserved job's 16 frames are tagged, the 17th is not, and a frame
                taken while an interrupt is serviced is not.";
            attribute :>> parent = "H.QUOTA.15";
            attribute :>> unit = ("mm::reservation::drawn", "mm::reservation::room",
                "mm::reservation_for", "irq::in_interrupt", "irq::serviced",
                "irq::servicing", "irq::dispatch", "trap::service_interrupts");
        }
        requirement <'L.mm.80'> aFreedFrameGoesBackToItsPromise : ItemLowLevel {
            attribute :>> statement = "A frame tagged with a reservation shall,
                in the hold that frees it, leave the reservation's drawn count,
                give O back what that makes outstanding again, and lose its
                tag, and so when it is retired, where the free count does not get
                it back, up to the retired set's capacity; the RAM scrubber shall
                claim nothing below twice the watermark beyond O; an unbound
                reservation shall promise nothing and be bound again only once
                nothing is drawn from it.";
            attribute :>> criterion = "At stage 2 a drawn frame retired leaves the
                reservation with the free count unchanged, the scrubber claims nothing
                while a promise covers its margin, the 64 drawn frames freed bring
                O back to 64 and leave no tag, and the reservation unbound brings
                O back to what it was; at stage 9 a gone job's reservation
                promises nothing.";
            attribute :>> parent = "H.QUOTA.15";
            attribute :>> unit = ("mm::reservation::freed", "mm::reservation::adjust",
                "mm::reservation::unbind", "mm::deallocate_frames", "mm::release_frame",
                "mm::reservation::tag_of", "mm::reservation::drawn_from",
                "mm::reservation::install", "mm::place_tags");
        }
        requirement <'L.mm.81'> aReservationHasItsOwnHeap : ItemLowLevel {
            attribute :>> statement = "An allocation by a task whose job draws
                from a reservation, or by a task inside a heap scope on one
                (L.mm.140), in task context, shall be served by that
                reservation's own heap, whose pages are drawn from it alone,
                or for a request above a page the buddy has no run for by the
                large-request area from frames drawn from it alone (L.mm.141),
                and by the shared heap only once it has no room; every other
                allocation by the shared heap, whose pages are never drawn; a
                heap object shall be freed to the heap its page's tag names,
                and a large block by the area, each frame to its tag's
                reservation (L.mm.142);
                and a free entry's heap shall give back the empty pages it keeps
                before the entry is bound again, so that a reservation of any
                size is whole.";
            attribute :>> criterion = "At stage 9 a reserved job's 32 objects lie
                on pages tagged with its reservation, a sibling's 32 of the same
                size class and one made while an interrupt is serviced on
                untagged pages, and once freed they are back on its heap with at
                most a page a size class drawn. A new job's reservation of 4
                frames on an entry whose heap kept more reads none drawn and is
                given all 4. Control: bind leaving the kept pages.";
            attribute :>> parent = "H.QUOTA.15";
            attribute :>> unit = ("mm::KernelAllocator::alloc", "mm::KernelAllocator::dealloc",
                "mm::from_shared_heap", "mm::ReservedPages::allocate_pages", "mm::ReservedPages::deallocate_pages",
                "mm::reserved_heap", "mm::heap_drawn_from", "mm::reservation_bind",
                "mm::reservation::bind");
        }
        requirement <'L.mm.82'> aReclaimLiftsOverThePromise : ItemLowLevel {
            attribute :>> statement = "program_floor shall answer W + O, the
                least free count a program's frame not drawn from a reservation is
                given at, which a machine-wide reclaim for a frame lifts the free
                count over (the load's fs::pages::reclaim_want).";
            attribute :>> criterion = "At stage 2, with 64 frames promised,
                program_floor answers W + 64, and program frames taken until
                refused leave exactly that free; test-btrfs-pressure writes and
                deletes its GiBs with no ENOSPC.";
            attribute :>> parent = "H.QUOTA.15";
            attribute :>> unit = "mm::program_floor";
        }
        requirement <'L.user.145'> aReclaimSparesAnothersReservation : ItemLowLevel {
            attribute :>> statement = "A reclaim shall not take a frame drawn from
                a reservation other than the one the running task's job draws
                from, nor any drawn frame in interrupt context.";
            attribute :>> criterion = "At stage 9 a frame drawn from a job's
                reservation is spared for a reclaim drawing from none and taken
                for one drawing from it, and an undrawn frame is taken.";
            attribute :>> parent = "H.QUOTA.17";
            attribute :>> unit = ("user::cache::spares", "user::cache::reclaim",
                "user::cache::take_from");
        }
    }

    package AllocationReserve {
        doc /* src/kernel/src/mm/reserve.rs: each processor's allocation reserve, which
             * lets an Arc or a map insert that has started finish (finding F-23). */

        requirement <'L.mm.35'> aSectionCompletesOnTheReserve : ItemLowLevel {
            attribute :>> statement = "Inside a reserved section, an allocation the
                heap does not serve shall be served from the processor's reserve, a
                block of its size class or the large block held for it, so that the
                section's operation completes.";
            attribute :>> criterion = "With every allocation inside a section sent to
                the reserve without asking the heap, an Arc of 64 bytes, an Arc of 3000
                bytes (past the largest size class) and 200 map inserts each complete
                and hold what was put in them, and the reserve is drawn on at least 4
                times.";
            attribute :>> parent = "H.MEM.11";
            attribute :>> unit = ("mm::reserve::reserve", "mm::reserve::enter",
                "mm::reserve::slot", "mm::reserve::draw", "mm::reserve::leave",
                "mm::reserve::Reserved::drop", "mm::KernelAllocator::alloc",
                "mm::reserve::bypassing_heap");
        }
        requirement <'L.mm.36'> aSectionThatCannotFillIsRefused : ItemLowLevel {
            attribute :>> statement = "reserve and fill_reserve shall refuse with
                AllocError, count the refusal and leave interrupts as they found them,
                when the heap cannot fill the processor's reserve or hold the large
                block asked for.";
            attribute :>> criterion = "With the heap unable to take a page and the
                reserve drawn below its depth, reserve is refused AllocError, the
                refused count rises by 1, and interrupts are enabled after as before;
                the same for a large block the heap cannot supply.";
            attribute :>> parent = "H.MEM.11";
            attribute :>> unit = ("mm::reserve::reserve", "mm::reserve::enter",
                "mm::reserve::fill_reserve");
        }
        requirement <'L.mm.37'> theReserveServesOnlyItsSections : ItemLowLevel {
            attribute :>> statement = "draw shall serve an allocation from a reserve
                only while a section is open on that processor, but for the task killing
                for the kernel's heap outside any section (L.mm.139).";
            attribute :>> criterion = "With the heap unable to take a page, an
                allocation made outside any section by a task that is not the heap's
                killer is refused and the drawn count is unchanged, while the same
                allocation inside a section is served.";
            attribute :>> parent = "H.MEM.11";
            attribute :>> unit = ("mm::reserve::draw", "mm::reserve::slot");
        }
        requirement <'L.mm.38'> aLargeBlockGoesBackWithTheSection : ItemLowLevel {
            attribute :>> statement = "When the outermost section on a processor
                closes, leave shall give a large block that section did not use back
                to the heap.";
            attribute :>> criterion = "A section entered for a large Arc and closed
                without making it leaves the heap's large pages and the free frame
                count where they were before the section.";
            attribute :>> parent = "H.MEM.9";
            attribute :>> unit = ("mm::reserve::leave", "mm::reserve::Reserved::drop");
        }
    }

    package UnlinkedTables {
        doc /* src/kernel/src/mm/unlinked.rs: page tables an unmap has unlinked from a
             * live tree, held from the allocator until the shootdown or the unit's
             * invalidation that covers them (finding F-36). */

        requirement <'L.mm.39'> theShootdownGivesBackTheHeldTables : ItemLowLevel {
            attribute :>> statement = "UnlinkedTables::release, called once the
                shootdown covering the unmap has returned, shall give every table on the
                list back to the frame allocator, counting a user tree's as user
                tables.";
            attribute :>> criterion = "The shootdown for an unmap_in that emptied
                tables leaves the list empty, and the user tables given back rise by
                exactly the number it held.";
            attribute :>> parent = "H.MEM.7";
            attribute :>> unit = ("mm::unlinked::UnlinkedTables::release",
                "mm::unlinked::UnlinkedTables::pop");
        }
        requirement <'L.mm.40'> mergedShootdownsKeepEveryTable : ItemLowLevel {
            attribute :>> statement = "take_from shall move every table of one list
                onto another, so that shootdowns merged into one release the tables of
                both, and none before it.";
            attribute :>> criterion = "Two lists of 2 and 3 tables merged with
                take_from leave the first empty and the second holding 5, all 5 still
                allocated; releasing the second gives back 5.";
            attribute :>> parent = "H.MEM.7";
            attribute :>> unit = ("mm::unlinked::UnlinkedTables::take_from",
                "mm::unlinked::UnlinkedTables::push",
                "mm::unlinked::UnlinkedTables::pop");
        }
        requirement <'L.mm.41'> aDroppedListKeepsItsTables : ItemLowLevel {
            attribute :>> statement = "A list dropped while it still holds tables
                shall keep them from the frame allocator for good and count them.";
            attribute :>> criterion = "A list holding 1 table, dropped unreleased,
                raises tables_kept by 1 and the table stays allocated: claim_frame
                refuses it.";
            attribute :>> parent = "H.MEM.7";
            attribute :>> unit = "mm::unlinked::UnlinkedTables::drop";
        }
    }

    package KernelArena {
        doc /* src/kernel/src/vmap.rs: the kernel's dynamic address space -- anonymous
             * allocations, device windows, buffers and guard-paged kernel stacks.
             * check_failed_device_map and check_invariants are check code in this
             * product file (mm-draft-A-notes.md). */

        requirement <'L.mm.42'> arenaAllocationsAreApart : ItemLowLevel {
            attribute :>> statement = "vmap::allocate shall hand out address ranges
                inside the arena, no two of them sharing an address or a guard page.";
            attribute :>> criterion = "Two live 8-page allocations have different
                bases, lie inside ARENA_BASE..ARENA_END, and the higher begins at least
                two pages past the end of the lower.";
            attribute :>> parent = "H.MEM.14";
            attribute :>> unit = ("vmap::init", "vmap::allocate", "vmap::reserve");
        }
        requirement <'L.mm.43'> arenaAllocationsAreGuarded : ItemLowLevel {
            attribute :>> statement = "vmap::allocate shall leave the page directly
                below and the page directly above every allocation unmapped.";
            attribute :>> criterion = "The page below an 8-page allocation and the page
                at its end do not translate.";
            attribute :>> parent = "H.FAIL.2";
            attribute :>> unit = ("vmap::allocate", "vmap::reserve", "vmap::allocate_below", "vmap::reserve_below");
        }
        requirement <'L.mm.44'> arenaPagesAreTheirOwnFrames : ItemLowLevel {
            attribute :>> statement = "vmap::allocate shall back each page of an
                allocation with a writable frame of its own.";
            attribute :>> criterion = "Each of the 8 pages of a fresh allocation
                translates, and a different value written to the first word of each is
                read back from every page after all 8 are written.";
            attribute :>> parent = "H.MEM.14";
            attribute :>> unit = ("vmap::allocate", "mm::map_kernel");
        }
        requirement <'L.mm.45'> arenaPagesAreZeroed : ItemLowLevel {
            attribute :>> statement = "vmap::allocate shall zero every byte of each
                page before mapping it.";
            attribute :>> criterion = "An 8-page allocation made after 8 frames were
                filled with a pattern and given back reads 0 in every byte of every
                page, 32768 of 32768.";
            attribute :>> parent = "H.MEM.6";
            attribute :>> unit = ("vmap::allocate", "mm::zero_frame");
        }
        requirement <'L.mm.46'> freeGivesTheAllocationBack : ItemLowLevel {
            attribute :>> statement = "vmap::free shall unmap an allocation and give
                all its frames back, and shall refuse an address it has already taken
                back.";
            attribute :>> criterion = "Two 8-page allocations are freed; a second free
                of the first is refused; its base no longer translates; and the free
                frame count is back where it stood after a warm-up pair had been made
                and freed.";
            attribute :>> parent = "H.MEM.9";
            attribute :>> unit = ("vmap::free", "vmap::claim", "vmap::release_span",
                "mm::unmap_kernel_all", "mm::deallocate_frames");
        }
        requirement <'L.mm.47'> anEmptyAllocationIsRefused : ItemLowLevel {
            attribute :>> statement = "vmap::allocate shall refuse an allocation of
                zero pages as a bad length.";
            attribute :>> criterion = "An allocation of 0 pages is refused
                BadLength(0).";
            attribute :>> parent = "H.MEM.15";
            attribute :>> unit = ("vmap::allocate", "vmap::reserve");
        }
        requirement <'L.mm.48'> aFailedAllocationKeepsNoFrame : ItemLowLevel {
            attribute :>> statement = "vmap::allocate, allocate_stack and free_stacks
                shall answer an allocation refused part way as running out of memory,
                undoing what was done, and keep no frame of it.";
            attribute :>> criterion = "With each allocation that making three kernel
                stacks and freeing them -- one alone, then two in one call -- makes
                failed in turn, frames included, every run ends in success or as
                running out of memory, and the frame window alloc_check's run opens
                around the runs keeps 0 frames.";
            attribute :>> parent = "H.MEM.11";
            attribute :>> unit = ("vmap::allocate", "vmap::unwind", "vmap::release",
                "vmap::release_span", "vmap::allocate_stack", "vmap::allocate_stack_of", "vmap::free_stacks",
                "mm::allocate_frames");
        }
        requirement <'L.mm.49'> deviceWindowsLandWhereAsked : ItemLowLevel {
            attribute :>> statement = "map_device shall map a device window as device
                memory, not executable, at an address with the same offset in its page
                as the physical address asked for, and unmap_device shall take it down
                without giving the aperture's frames to the allocator.";
            attribute :>> criterion = "A window of 0x100 bytes at offset 0x40 into a
                frame starts at offset 0x40 in its page, translates to the address
                asked for and is mapped device and not executable; unmapped, it no
                longer translates and the free frame count is unchanged.";
            attribute :>> parent = ("H.MEM.15", "H.MEM.14");
            attribute :>> unit = ("vmap::map_device", "vmap::map_reserved",
                "vmap::unmap_device", "vmap::free", "mm::map_kernel");
        }
        requirement <'L.mm.50'> deviceWindowsRefuseTheImage : ItemLowLevel {
            attribute :>> statement = "map_device shall refuse, before it reserves or
                maps anything, a range that touches any byte of the kernel image.";
            attribute :>> criterion = "Windows asked for over the image's first 0x100
                bytes, a two-page range from the page below it into it, its last byte
                and a page at its middle are each refused KernelImage naming the
                address asked for, 4 of 4, and the arena holds as many allocations as
                before.";
            attribute :>> parent = "H.MEM.10";
            attribute :>> unit = ("vmap::map_device", "mm::overlaps_image",
                "mm::image_span_overlaps", "vmap::usage", "vmap::VmapError::fmt");
        }
        requirement <'L.mm.51'> deviceWindowsRefuseAWrappedRange : ItemLowLevel {
            attribute :>> statement = "map_device shall refuse as a bad length, before
                it reserves anything, a range whose end rounded out to a page is past
                the top of the address space.";
            attribute :>> criterion = "Four ranges that wrap -- the offset plus the
                length, the rounding of that, the top page with a page's length, and
                0x100 bytes at 0x40 into the top page -- are each refused BadLength
                naming the length asked for, 4 of 4, and the arena holds as many
                allocations as before.";
            attribute :>> parent = "H.MEM.15";
            attribute :>> unit = ("vmap::map_device", "vmap::usage");
        }
        requirement <'L.mm.52'> aFailedDeviceMapLeavesNothing : ItemLowLevel {
            attribute :>> statement = "A device window whose mapping fails part way
                shall leave none of its own pages mapped and remove no mapping it did
                not make.";
            attribute :>> criterion = "A two-page window whose second page is already
                mapped is refused, its first page does not translate afterwards, and
                the mapping in its way still translates to where it did.";
            attribute :>> parent = "H.MEM.15";
            attribute :>> unit = ("vmap::map_reserved", "vmap::unmap_installed");
        }
        requirement <'L.mm.53'> theArenaStaysConsistent : ItemLowLevel {
            attribute :>> statement = "The arena's regions shall stay sorted and
                non-overlapping, and every live allocation's span shall stay reserved
                in it, through every reserve, claim and release.";
            attribute :>> criterion = "After the stage 2 arena checks' allocations,
                windows and frees, the arena's regions are sorted and do not overlap,
                and each live allocation's span is found in it, 0 exceptions.";
            attribute :>> parent = "H.MEM.14";
            attribute :>> unit = ("vmap::reserve", "vmap::claim", "vmap::release",
                "vmap::release_span");
        }
        requirement <'L.mm.54'> deviceWindowsAreListed : ItemLowLevel {
            attribute :>> statement = "device_windows shall list the physical range of
                every live device window and nothing an anonymous allocation holds.";
            attribute :>> criterion = "With one device window over a known frame and
                one anonymous allocation live, device_windows lists the window's range
                and no range of the anonymous allocation's frames; with the window
                gone, it no longer lists it.";
            attribute :>> parent = "H.DMA.5";
            attribute :>> unit = "vmap::device_windows";
        }
        requirement <'L.mm.55'> kernelStacksAreGuarded : ItemLowLevel {
            attribute :>> statement = "allocate_stack shall make a kernel stack of
                STACK_PAGES pages, and allocate_stack_of one of the pages asked, its top 16-byte aligned and every byte of it
                writable, with an unmapped page directly below and above it, and
                free_stack shall give all its frames back.";
            attribute :>> criterion = "A stack from allocate_stack is STACK_PAGES pages long, and one from
                allocate_stack_of at the boot stack's 16 is 16, with
                its top 16-byte aligned; a value written at its first word and at its
                last is read back; the STACK_LOWER_GUARD_PAGES pages below its base and
                the page at its top do not translate; and free_stack returns the free frame count to where it
                was.";
            attribute :>> parent = ("H.FAIL.2", "H.MEM.9");
            attribute :>> unit = ("vmap::allocate_stack", "vmap::allocate_stack_of", "vmap::free_stack");
        }
        requirement <'L.mm.56'> stacksAreFreedUnderOneShootdown : ItemLowLevel {
            attribute :>> statement = "free_stacks shall take every stack it is given
                out of use, unmap all of them under one shootdown, and make their
                addresses available again only after it.";
            attribute :>> criterion = "Freeing 8 stacks with free_stacks takes exactly
                1 shootdown, gives back every frame, and none of the 8 addresses is
                handed out again before the shootdown has returned.";
            attribute :>> parent = "H.MEM.14";
            attribute :>> unit = "vmap::free_stacks";
        }
        requirement <'L.mm.57'> aBufferIsZeroedPages : ItemLowLevel {
            attribute :>> statement = "Buffer::zeroed shall make a buffer of len
                zeroed bytes on pages that need not be contiguous, none for a length of
                zero, and the buffer's drop shall free them.";
            attribute :>> criterion = "A buffer of 5 MiB, more than the heap's largest
                block, reads 0 in every byte and holds what is written; a buffer of 0
                bytes takes no allocation; with both dropped the arena's allocations
                and the free frame count are where they were.";
            attribute :>> parent = ("H.MEM.6", "H.MEM.9");
            attribute :>> unit = ("vmap::Buffer::zeroed", "vmap::Buffer::deref",
                "vmap::Buffer::deref_mut", "vmap::Buffer::drop",
                "vmap::Buffer::truncate");
        }
    }

    package EarlyMemory {
        doc /* src/kernel/src/early.rs: physical memory and page tables before there is
             * a frame allocator -- the loader's tables extended from a pool of
             * sixteen frames in .bss. read_physical_byte and translate serve only
             * stage 1's checks, which are in main.rs (mm-draft-A-notes.md). */

        requirement <'L.mm.58'> earlyWindowsTranslateAsAsked : ItemLowLevel {
            attribute :>> statement = "map_device and map_framebuffer shall install in
                the loader's tables a window that translates each page to the physical
                address asked for, with device or framebuffer attributes.";
            attribute :>> criterion = "The framebuffer window, where firmware left one
                outside reclaimable memory, translates to the framebuffer's physical
                address; a device window translates to the registers asked for and is
                mapped device and not executable.";
            attribute :>> parent = ("H.BOOT.1", "H.MEM.15");
            attribute :>> unit = ("early::EarlyMemory::new",
                "early::EarlyMemory::map_window", "early::EarlyMemory::map_device",
                "early::EarlyMemory::map_framebuffer",
                "early::EarlyMemory::read", "early::EarlyMemory::write");
        }
        requirement <'L.mm.59'> earlyWindowsRefuseTheImage : ItemLowLevel {
            attribute :>> statement = "map_window shall refuse, before it maps
                anything, a range that touches any byte of the kernel image.";
            attribute :>> criterion = "Early device windows asked for over the image's
                first page, a range straddling its start, its last byte and a range
                straddling its end are each refused KernelImage naming the address
                asked for, 4 of 4, and the window address still does not translate.";
            attribute :>> parent = "H.MEM.10";
            attribute :>> unit = ("early::EarlyMemory::map_window",
                "mm::image_span_overlaps");
        }
        requirement <'L.mm.60'> earlyWindowsRefuseAWrappedRange : ItemLowLevel {
            attribute :>> statement = "map_window shall refuse with RangeOverflow,
                before it judges the range against the image or maps anything, a range
                whose end rounded out to a page is past the top of the address
                space.";
            attribute :>> criterion = "The top page with a page's length and a page
                with a length of 2^64 - 1 are each refused MapFailed(RangeOverflow), 2
                of 2, and the window address still does not translate.";
            attribute :>> parent = "H.MEM.15";
            attribute :>> unit = "early::EarlyMemory::map_window";
        }
        requirement <'L.mm.61'> theEarlyTablePoolIsBounded : ItemLowLevel {
            attribute :>> statement = "EarlyMemory::allocate_table shall hand out each
                of its 16 pool frames at most once and then refuse, which a mapping
                reports as running out of memory.";
            attribute :>> criterion = "An EarlyMemory asked for 17 tables answers 16
                distinct page-aligned frames inside the pool and then none; a mapping
                that needs a table after that is refused MapFailed(OutOfMemory).";
            attribute :>> parent = "H.MEM.14";
            attribute :>> unit = "early::EarlyMemory::allocate_table";
        }
        requirement <'L.mm.62'> onlyRamHasACheckedDirectMapAlias : ItemLowLevel {
            attribute :>> statement = "direct_map_ram shall answer a direct-map address
                only for a physical address inside a run of RAM that record_ram
                recorded from the memory map, clipped to the direct map's span, and
                record_ram shall record those runs whole, in whole pages, ascending
                and apart, or refuse to bring memory up.";
            attribute :>> criterion = "At least one run is recorded, each whole pages,
                ascending and apart; a frame the allocator hands out is answered with
                the direct_map address; the page past the highest run, a page between
                two runs where the memory map has one, and a device's aperture are
                each answered None (the stage 2 memory check and the `copies` line).";
            attribute :>> parent = ("H.MEM.1", "H.MEM.15");
            attribute :>> unit = ("mm::direct_map_ram", "mm::record_ram");
        }
        requirement <'L.mm.63'> aLibraryMapInsertRunsInASection : ItemLowLevel {
            attribute :>> statement = "A library crate's map insert through
                ferrix_fallible shall run in a reserved section the kernel installs at
                boot: completed from the reserve when the heap refuses, refused before
                it starts when the reserve cannot be filled, and refused when its nodes
                are larger than any size class.";
            attribute :>> criterion = "With every allocation inside a section sent to the
                reserve, 200 inserts through ferrix_fallible::try_map_insert complete,
                hold what was inserted and draw on the reserve at least twice; with the
                checking processor's fills refused, an insert is refused, the refused
                count rises and the map is unchanged; a map of 256-byte values is
                refused.";
            attribute :>> parent = "H.MEM.11";
            attribute :>> unit = ("fallible::library_section",
                "fallible::install_library_sections");
        }
        requirement <'L.mm.64'> refusedFillsStayOnOneProcessor : ItemLowLevel {
            attribute :>> statement = "refuse_reserve_fills shall make every section
                entered on the calling processor refused, as if its reserve could not be
                filled, until it is turned off.";
            attribute :>> criterion = "With fills refused, a library map insert on the
                checking processor is refused and the refused count rises; turned off
                again, the next insert completes.";
            attribute :>> parent = "H.MEM.11";
            attribute :>> unit = ("mm::reserve::refuse_reserve_fills",
                "mm::reserve::this_cpu_tag");
        }
    }

    package VirtualMemoryObjects {
        doc /* src/kernel/src/user/vmo.rs: the pageable memory object -- a sparse
             * list of frames committed on first touch, shared by a fork until
             * a write copies, held in place for a device, moved by mremap, cut
             * by a file's truncation -- and the three phases a page leaves it
             * by: out of the list, forgotten by every space that maps it and
             * shot down, and only then released. */

        requirement <'L.user.1'> aReservationCostsNothing : ItemLowLevel {
            attribute :>> statement = "Vmo::new_anonymous shall make an object of
                the pages asked for with no page committed and no frame taken.";
            attribute :>> criterion = "A fresh object of 1024 pages has 0 pages
                committed, the free-frame count is what it was before it was made,
                and its size reads 1024 pages and 1024 x 4096 bytes.";
            attribute :>> parent = "H.QUOTA.2";
            attribute :>> unit = ("user::vmo::Vmo::new_anonymous",
                "user::vmo::Vmo::unfilled", "user::vmo::Vmo::committed",
                "user::vmo::Vmo::len_pages", "user::vmo::Vmo::len_bytes");
        }
        requirement <'L.user.2'> aCommittedPageIsZeroed : ItemLowLevel {
            attribute :>> statement = "Vmo::commit shall give a page its first
                frame filled with zeros.";
            attribute :>> criterion = "Page 2 of a fresh 4-page object, committed,
                reads 0 in each of its 4096 bytes through the direct map.";
            attribute :>> parent = "H.MEM.6";
            attribute :>> unit = "user::vmo::Vmo::commit";
        }
        requirement <'L.user.3'> aFirstWriteCommitsAZeroedPage : ItemLowLevel {
            attribute :>> statement = "Vmo::write_page to a page that holds no
                frame shall commit a zeroed frame before it writes, so that the
                bytes of the page it does not write read as 0.";
            attribute :>> criterion = "A frame filled with a pattern and freed is
                taken by a write of 8 bytes at offset 100 of an uncommitted page;
                the other 4088 bytes of the page read 0.";
            attribute :>> parent = "H.MEM.6";
            attribute :>> unit = ("user::vmo::Vmo::write_page",
                "user::vmo::Pages::exclusive");
        }
        requirement <'L.user.4'> commitIsIdempotent : ItemLowLevel {
            attribute :>> statement = "Vmo::commit of a page that holds a frame
                shall hand back that frame and take no other.";
            attribute :>> criterion = "Page 3 committed twice gives the same frame
                both times, the second commit taking 0 frames; the object names that
                frame at page 3 and none at the untouched page 4.";
            attribute :>> parent = "H.QUOTA.2";
            attribute :>> unit = ("user::vmo::Vmo::commit", "user::vmo::Vmo::page");
        }
        requirement <'L.user.5'> commitRefusesPastTheEnd : ItemLowLevel {
            attribute :>> statement = "Vmo::commit shall refuse a page at or past
                the object's end as OutOfRange, naming the page and the object's
                size, and take no frame for it.";
            attribute :>> criterion = "commit of page 4 of a 4-page object is
                refused OutOfRange { index: 4, pages: 4 }, and the object has 0
                pages committed after.";
            attribute :>> parent = "H.MEM.1";
            attribute :>> unit = ("user::vmo::Vmo::commit", "user::vmo::VmoError::fmt");
        }
        requirement <'L.user.6'> commitWithinRefusesPastTheEnd : ItemLowLevel {
            attribute :>> statement = "Vmo::commit_within shall refuse a page at or
                past the object's end as OutOfRange, naming the page and the
                object's size.";
            attribute :>> criterion = "commit_within of page 1 of a 1-page object
                is refused OutOfRange { index: 1, pages: 1 }.";
            attribute :>> parent = "H.MEM.1";
            attribute :>> unit = "user::vmo::Vmo::commit_within";
        }
        requirement <'L.user.7'> onlyWhatIsTouchedIsPaidFor : ItemLowLevel {
            attribute :>> statement = "Vmo::commit shall take one frame for each
                distinct page committed and no more, and dropping the object shall
                give every one of them back.";
            attribute :>> criterion = "Of a 2048-page object, 7 scattered pages
                committed out of order leave exactly 7 committed and the free-frame
                count 7 lower; with the object dropped the count is what it was
                before it was made.";
            attribute :>> parent = ("H.QUOTA.2", "H.MEM.9");
            attribute :>> unit = ("user::vmo::Vmo::commit", "user::vmo::Vmo::committed",
                "user::vmo::Vmo::drop");
        }
        requirement <'L.user.8'> aSharedFrameOutlivesOneHolder : ItemLowLevel {
            attribute :>> statement = "Dropping an object shall give back its own
                reference on each frame it holds, and so free only the frames no
                other holder still references.";
            attribute :>> criterion = "A committed page given a second reference:
                with the object dropped the frame has 1 reference and is not free
                (the free count 1 below where it began); with the last reference
                released the count is back where it began.";
            attribute :>> parent = ("H.MEM.9", "H.MEM.8");
            attribute :>> unit = "user::vmo::Vmo::drop";
        }
        requirement <'L.user.9'> aVmoIsCountedAsAnObject : ItemLowLevel {
            attribute :>> statement = "Vmo::new_anonymous and Vmo::fork shall each
                charge one object to the running task's job for as long as the
                object lives, and be refused, making nothing, when the job's object
                limit is full; Vmo::new_filled, a file's page cache, shall charge
                none.";
            attribute :>> criterion = "In a job limited to 5 objects and holding 5,
                vmo_create is refused NO_MEMORY and a fork of an object is refused,
                0 objects counted beyond the limit; with every object dropped the
                job holds 0; a tmpfs file made in the job adds 0 objects.";
            attribute :>> parent = ("H.QUOTA.9", "H.QUOTA.4");
            attribute :>> unit = ("user::vmo::Vmo::new_anonymous",
                "user::vmo::Vmo::fork", "user::vmo::Vmo::new_filled");
        }
        requirement <'L.user.10'> anUncommittedPageReadsAsZeros : ItemLowLevel {
            attribute :>> statement = "Vmo::read_page of a page that holds no frame
                shall read zeros and commit nothing.";
            attribute :>> criterion = "A read of 4096 bytes of page 5 of a fresh
                8-page object returns 4096 zeros, and the object has 0 pages
                committed and the free-frame count is unchanged after.";
            attribute :>> parent = ("H.MEM.6", "H.QUOTA.2");
            attribute :>> unit = "user::vmo::Vmo::read_page";
        }
        requirement <'L.user.11'> aByteRangeLeavingThePageIsRefused : ItemLowLevel {
            attribute :>> statement = "Vmo::read_page and Vmo::write_page shall
                refuse, as OutOfRange and copying nothing, a page past the object's
                end or a byte range that runs past the end of its page.";
            attribute :>> criterion = "Of a 2-page object, a read and a write of
                page 2, and of 8 bytes at offset 4092 of page 0, and of a range
                whose end overflows, are each refused OutOfRange, 6 of 6, with 0
                pages committed and the caller's buffer unchanged.";
            attribute :>> parent = "H.MEM.1";
            attribute :>> unit = ("user::vmo::Vmo::check_span",
                "user::vmo::Vmo::read_page", "user::vmo::Vmo::write_page");
        }
        requirement <'L.user.12'> forkSharesAndAWriteCopies : ItemLowLevel {
            attribute :>> statement = "Vmo::fork shall give the new object each
                committed page by a further reference to the same frame, and
                Vmo::write_page to a page another object shares shall copy it
                first, so that the write is not seen through the other object.";
            attribute :>> criterion = "A 1-page object written `before` and forked
                names the same frame as its fork; `after!` written through the
                original moves it to another frame, and the original reads
                `after!` while the fork reads `before`.";
            attribute :>> parent = "H.MEM.8";
            attribute :>> unit = ("user::vmo::Vmo::fork", "user::vmo::Vmo::write_page",
                "user::vmo::Pages::exclusive", "user::vmo::Vmo::read_page");
        }
        requirement <'L.user.13'> aDisplacedSharedFrameIsTakenDown : ItemLowLevel {
            attribute :>> statement = "When Vmo::write_page copies a shared page, it
                shall have every address space that maps the object forget the
                page, invalidated on every processor that may hold it, before it
                gives back the object's reference on the original, so that a
                mapping faults the copy in.";
            attribute :>> criterion = "A shared object a process maps and reads on
                another processor, whose page a fork of the object shares, written
                through Vmo::write_page: the process then reads the bytes written,
                not the original's, and its space translates the page to the
                copy.";
            attribute :>> parent = ("H.MEM.17", "H.MEM.8");
            attribute :>> unit = ("user::vmo::Vmo::write_page", "user::vmo::Vmo::retire",
                "user::vmo::Vmo::retire_runs");
        }
        requirement <'L.user.14'> aReplaceGivesBackTheOldReference : ItemLowLevel {
            attribute :>> statement = "Vmo::replace shall put the new frame in the
                page, return the frame it displaced, and give back only the
                object's own reference on that frame.";
            attribute :>> criterion = "Replacing a page whose frame has a second
                holder returns that frame, the object names the new frame, and the
                old frame has 1 reference; with the other holder's release and the
                object dropped the free-frame count is back where it began, 0
                frames kept.";
            attribute :>> parent = ("H.MEM.8", "H.MEM.9");
            attribute :>> unit = ("user::vmo::Vmo::replace", "user::vmo::Vmo::take_page",
                "user::vmo::Retired::with_room", "user::vmo::Retired::frame",
                "user::vmo::Vmo::retire", "user::vmo::Vmo::retire_runs",
                "user::vmo::Vmo::drop");
        }
        requirement <'L.user.15'> aReplaceOfAnAbsentPageDisplacesNothing : ItemLowLevel {
            attribute :>> statement = "Vmo::replace of a page that holds no frame
                shall put the frame in and report nothing displaced.";
            attribute :>> criterion = "A replace of page 1 of a 2-page object with
                nothing committed returns nothing, and the object then names the
                frame given at page 1.";
            attribute :>> parent = "H.MEM.8";
            attribute :>> unit = ("user::vmo::Vmo::replace", "user::vmo::Vmo::take_page");
        }
        requirement <'L.user.16'> decommitReachesEveryMapper : ItemLowLevel {
            attribute :>> statement = "Vmo::decommit_range shall take a page out of
                every address space that maps the object, invalidated on every
                processor that may hold its translation, before the page's frame
                goes back to the allocator.";
            attribute :>> criterion = "On two or more processors, a page of a
                shared object that two processes on two processors have touched
                (rmap_check::check's setup) is decommitted: 1 page given back,
                neither space translates it, the kernel claims the freed frame and
                poisons it, and the process on the other processor then reads 0,
                not the poison, and writes to a new frame, the freed one keeping its
                poison.";
            attribute :>> parent = ("H.MEM.17", "H.MEM.6");
            attribute :>> unit = ("user::vmo::Vmo::decommit_range",
                "user::vmo::Vmo::take_range", "user::vmo::Pages::take_into",
                "user::vmo::Vmo::retire", "user::vmo::Vmo::retire_runs",
                "user::vmo::runs_of", "user::vmo::Vmo::mapped_by",
                "user::vmo::forget_together");
        }
        requirement <'L.user.17'> replaceReachesEveryMapper : ItemLowLevel {
            attribute :>> statement = "Vmo::replace shall take the page out of every
                address space that maps the object, invalidated on every processor
                that may hold its translation, before it gives back the displaced
                frame, so that every mapping reaches the new frame.";
            attribute :>> criterion = "On two or more processors, a page of a
                shared object two processes on two processors have touched
                (rmap_check::check's setup) is replaced with a frame holding a
                pattern: the displaced frame is returned, neither space translates
                the page, the kernel poisons the displaced frame, and the process on
                the other processor reads the pattern, not the poison, and writes
                into the new frame, as the other process then does.";
            attribute :>> parent = "H.MEM.17";
            attribute :>> unit = ("user::vmo::Vmo::replace", "user::vmo::Vmo::take_page",
                "user::vmo::Retired::frame", "user::vmo::Vmo::retire",
                "user::vmo::Vmo::retire_runs", "user::vmo::runs_of",
                "user::vmo::Vmo::mapped_by", "user::vmo::forget_together");
        }
        requirement <'L.user.18'> retireFoldsTheCallersShootdown : ItemLowLevel {
            attribute :>> statement = "Vmo::retire given the address space under
                whose lock phase one ran shall not ask that space again, shall run
                that space's pending shootdown together with the others', and shall
                release the frames only after every one has completed.";
            attribute :>> criterion = "A copy-on-write fault taken on one processor
                on a page the same space's thread has cached on another, finished
                through Vmo::take_page and Vmo::retire with its own space: the
                displaced frame, claimed back and poisoned once released, is never
                read by the other processor's thread, which reads the copy.";
            attribute :>> parent = "H.MEM.17";
            attribute :>> unit = ("user::vmo::Vmo::retire", "user::vmo::Vmo::retire_runs",
                "user::vmo::forget_together", "user::vmo::own_shootdown");
        }
        requirement <'L.user.19'> aDecommitNeedsNoMemory : ItemLowLevel {
            attribute :>> statement = "Vmo::decommit_range shall give back every page
                of its range that is not held, taken out of every space that maps
                the object, even when no allocation can be made: a chunk of pages
                at a time from the stack, and the spaces asked one at a time.";
            attribute :>> criterion = "80 pages of a mapped 160-page object,
                committed through faults, decommitted with every fallible
                allocation failing (at least 1 failed): 80 pages given back, 0 left
                committed, 0 still translated, and 0 frames kept.";
            attribute :>> parent = ("H.MEM.11", "H.MEM.9");
            attribute :>> unit = ("user::vmo::Vmo::decommit_range",
                "user::vmo::Vmo::decommit_in_chunks", "user::vmo::Pages::take_into",
                "user::vmo::runs_of", "user::vmo::Vmo::retire_runs",
                "user::vmo::Vmo::forget_one_at_a_time", "user::vmo::Vmo::next_mapper",
                "user::vmo::own_shootdown");
        }
        requirement <'L.user.20'> anAllocationFailureKeepsNothing : ItemLowLevel {
            attribute :>> statement = "Each operation of an object that allocates --
                commit, fork, write_page, hold, take_page, take_range, adopt_pages,
                attach, take_mapped_writes and a retirement's list of the spaces to
                ask -- shall answer a failed allocation as running out of memory, or
                carry on without the memory, and keep no frame.";
            attribute :>> criterion = "In the memory sweep, with each allocation of
                each scenario (fork, move, shared, split, cut, object, stacks, code)
                failed in turn, every run ends in success or in running out of
                memory, the run in which nothing failed succeeds, and each
                scenario's frame window keeps 0 frames (the `sweep` line).";
            attribute :>> parent = "H.MEM.11";
            attribute :>> unit = ("user::vmo::Vmo::commit", "user::vmo::Vmo::fork",
                "user::vmo::Vmo::write_page", "user::vmo::Vmo::hold",
                "user::vmo::Pages::count_held", "user::vmo::Vmo::take_page",
                "user::vmo::Vmo::take_range", "user::vmo::Vmo::adopt_pages",
                "user::vmo::Vmo::attach", "user::vmo::compact",
                "user::vmo::Vmo::take_mapped_writes", "user::vmo::Retired::with_room",
                "user::vmo::Retired::has_room", "user::vmo::Retired::record",
                "user::vmo::Vmo::mapped_by", "user::vmo::Vmo::forget_one_at_a_time");
        }
        requirement <'L.user.21'> holdingCopiesASharedPage : ItemLowLevel {
            attribute :>> statement = "Vmo::hold shall commit each page of its
                range, copying into a frame of its own a page a fork left shared,
                with its contents, and report the frames in page order.";
            attribute :>> criterion = "Holding pages 1 and 2 of a 4-page object
                whose page 1 a fork shares reports 2 frames, the ones the object
                names at pages 1 and 2; page 1's is not the shared frame and has 1
                reference, the fork still names the shared one, and page 1 still
                reads `held`.";
            attribute :>> parent = ("H.DMA.3", "H.MEM.8");
            attribute :>> unit = ("user::vmo::Vmo::hold", "user::vmo::Pages::unshared",
                "user::vmo::Pages::exclusive", "user::vmo::Pages::count_held",
                "user::vmo::Retired::with_room", "user::vmo::Vmo::retire",
                "user::vmo::Held::frames", "user::vmo::Vmo::commit_run",
                "user::vmo::Pages::insert_run");
        }
        requirement <'L.user.22'> aHeldPageKeepsItsFrame : ItemLowLevel {
            attribute :>> statement = "While a page is held, Vmo::decommit_range and
                Vmo::decommit_from shall skip it, Vmo::replace shall refuse it and
                leave the frame offered with the caller, and Vmo::write_page shall
                write it where it is.";
            attribute :>> criterion = "With pages 1 and 2 of a 4-page object held,
                decommit_range(0, 4) and decommit_from(0) each give back 0 pages and
                2 stay committed; a replace of page 1 returns nothing, page 1 keeps
                the held frame, and the frame offered is freed by the caller's
                release; a write to page 1 leaves it at the held frame.";
            attribute :>> parent = "H.DMA.3";
            attribute :>> unit = ("user::vmo::Vmo::decommit_range",
                "user::vmo::Vmo::decommit_from", "user::vmo::Vmo::take_range",
                "user::vmo::Pages::take_into", "user::vmo::Vmo::replace",
                "user::vmo::Vmo::take_page", "user::vmo::Vmo::write_page",
                "user::vmo::Vmo::give_back_run", "user::vmo::Pages::take_ours");
        }
        requirement <'L.user.23'> aHeldPageStaysMappedEverywhere : ItemLowLevel {
            attribute :>> statement = "While a page is held, Vmo::decommit_range and
                Vmo::replace shall leave it mapped at its frame in every address
                space that maps the object.";
            attribute :>> criterion = "On two or more processors, a page of a
                shared object two processes map (rmap_check::check's setup) is
                held: a write by one process reaches the held frame; decommit_range
                gives back 0 pages and a replace is refused, the object still naming
                the held frame; both spaces translate the page to the held frame
                before and after, and both processes read the marker written.";
            attribute :>> parent = "H.DMA.3";
            attribute :>> unit = ("user::vmo::Vmo::hold",
                "user::vmo::Vmo::decommit_range", "user::vmo::Vmo::take_range",
                "user::vmo::Pages::take_into", "user::vmo::Vmo::replace",
                "user::vmo::Vmo::take_page");
        }
        requirement <'L.user.24'> forkCopiesAHeldPage : ItemLowLevel {
            attribute :>> statement = "Vmo::fork shall give the new object a copy of
                a held page, with its contents, rather than a reference to the held
                frame.";
            attribute :>> criterion = "A fork of an object whose page 1 is held
                names another frame than the held one at page 1, the held frame
                keeps 1 reference, and the fork's page 1 reads `held`.";
            attribute :>> parent = ("H.DMA.3", "H.MEM.8");
            attribute :>> unit = ("user::vmo::Vmo::fork", "mm::share_frames",
                "user::vmo::share_into");
        }
        requirement <'L.user.25'> holdsNest : ItemLowLevel {
            attribute :>> statement = "A page shall stay held until the last Held
                covering it is dropped, and then be an ordinary page again.";
            attribute :>> criterion = "Page 2 held by two holds and page 1 by one:
                with the first hold dropped, decommit_range(0, 4) gives back 1 page
                and page 2 keeps its frame; with the second dropped it gives back 1
                page and 0 stay committed.";
            attribute :>> parent = "H.DMA.3";
            attribute :>> unit = ("user::vmo::Vmo::hold", "user::vmo::Held::drop",
                "user::vmo::Pages::count_held", "user::vmo::Pages::uncount_held");
        }
        requirement <'L.user.26'> aHoldOutsideTheObjectIsRefused : ItemLowLevel {
            attribute :>> statement = "Vmo::hold shall refuse a range of no pages
                and a range that runs past the object's end.";
            attribute :>> criterion = "Of a 4-page object, hold of 2 pages from
                page 3 and hold of 0 pages from page 0 are both refused.";
            attribute :>> parent = "H.DMA.3";
            attribute :>> unit = "user::vmo::Vmo::hold";
        }
        requirement <'L.user.27'> heldPagesComeBack : ItemLowLevel {
            attribute :>> statement = "Holding pages, copying them for a hold or a
                fork, and letting the holds go shall keep no frame once the objects
                and their holds are dropped.";
            attribute :>> criterion = "The free-frame count taken before and after
                the held-page scenario (a write, a fork, two holds, a refused
                replace, a fork while held, decommits) is the same: 0 frames
                kept.";
            attribute :>> parent = "H.MEM.9";
            attribute :>> unit = ("user::vmo::Held::drop", "user::vmo::Vmo::drop",
                "user::vmo::Vmo::retire", "user::vmo::Vmo::retire_runs");
        }
        requirement <'L.user.28'> aHeldRangeIsReported : ItemLowLevel {
            attribute :>> statement = "Vmo::holds_any shall say whether any page of
                a range is held.";
            attribute :>> criterion = "Of a 4-page object with page 2 held,
                holds_any is true for pages 0 to 3 and for page 2 alone, and false
                for pages 0 and 1 and for page 3; with the hold dropped, false for
                pages 0 to 3.";
            attribute :>> parent = "H.DMA.3";
            attribute :>> unit = "user::vmo::Vmo::holds_any";
        }
        requirement <'L.user.29'> aHeldPageDoesNotMove : ItemLowLevel {
            attribute :>> statement = "Vmo::adopt_pages shall refuse to move a range
                any page of which is held.";
            attribute :>> criterion = "An mremap that must move a private region,
                one of whose pages is held, is refused (SpaceError::OutOfMemory), 1
                refusal.";
            attribute :>> parent = "H.DMA.3";
            attribute :>> unit = "user::vmo::Vmo::adopt_pages";
        }
        requirement <'L.user.30'> aMoveTakesThePagesWithIt : ItemLowLevel {
            attribute :>> statement = "Vmo::adopt_pages shall name each committed
                page of the range in the new object at the same offset from the
                range's start, and Vmo::release_moved shall take them out of the old
                object, so that a private region an mremap moves reaches the pages
                it had.";
            attribute :>> criterion = "A two-page private mapping, written across
                its page boundary, grown to four pages by an mremap that must move
                it: at the new address its first page and the string across the
                boundary read as written and the old address reads nothing; shrunk
                to one page and moved to a fixed address, it still reads its first
                page as written. And with kernel objects alone, on every profile, the `core mem` line (user/rehome_check.rs::check_adopt_and_release, user/rehome_check.rs::check_a_move_reaches_the_pages).";
            attribute :>> parent = "H.MEM.1";
            attribute :>> unit = ("user::vmo::Vmo::adopt_pages",
                "user::vmo::Vmo::release_moved");
        }
        requirement <'L.user.31'> aFailedMoveIsUndone : ItemLowLevel {
            attribute :>> statement = "Vmo::disown_pages shall make the object the
                pages moved to forget every one without releasing a frame, and
                Vmo::adopt_pages refused for memory shall leave that object naming
                none, so that the object the pages came from still holds each once.";
            attribute :>> criterion = "An mremap of a written private region made to
                fail after its pages moved leaves the region reading what was
                written, each frame with the reference count it had, and 0 frames
                kept once the space is dropped.";
            attribute :>> parent = ("H.MEM.11", "H.MEM.9");
            attribute :>> unit = ("user::vmo::Vmo::disown_pages",
                "user::vmo::Vmo::adopt_pages");
        }
        requirement <'L.user.32'> theMappersAreCounted : ItemLowLevel {
            attribute :>> statement = "Vmo::attach shall record each address space
                that names the object, so that Vmo::mapper_count counts every live
                space that maps it.";
            attribute :>> criterion = "A shared object mapped by a process, and by
                the child forked from it, has a mapper count of 2 before either
                runs.";
            attribute :>> parent = "H.MEM.17";
            attribute :>> unit = ("user::vmo::Vmo::attach",
                "user::vmo::Vmo::mapper_count");
        }
        requirement <'L.user.33'> goneMappersArePruned : ItemLowLevel {
            attribute :>> statement = "Vmo::detach shall remove the one name it is
                given, the list shall drop spaces that have gone whenever it is
                taken, and it shall give back most of its room once it lists under a
                quarter of it.";
            attribute :>> criterion = "An object mapped 1000 times by one space
                under 1000 ids and 1 time by a second: with 999 ids unmapped and
                the second space dropped, mapper_count is 1, and the heap the list
                held is back within 4 entries' room of 1 mapper.";
            attribute :>> parent = ("H.MEM.17", "H.QUOTA.7");
            attribute :>> unit = ("user::vmo::Vmo::detach", "user::vmo::Vmo::attach",
                "user::vmo::compact");
        }
        requirement <'L.user.34'> aPrivateObjectHasOneMapper : ItemLowLevel {
            attribute :>> statement = "Vmo::attach shall stop the kernel with the
                PRIVATE_OBJECT_SHARED report rather than give an object that backs
                a private region a second mapper, or a private mapper to an object
                already mapped.";
            attribute :>> criterion = "A negative control, attaching a second
                mapper to an object with a private one, ends the boot with the
                PRIVATE_OBJECT_SHARED report; no mapping the kernel makes in a
                boot does so.";
            attribute :>> parent = ("H.MEM.8", "H.FAIL.1");
            attribute :>> unit = "user::vmo::Vmo::attach";
        }
        requirement <'L.user.35'> aMapperIsCharged : ItemLowLevel {
            attribute :>> statement = "Vmo::attach shall charge the heap one name of
                an object holds against the running job's memory limit, record
                nothing when the charge is refused, and the charge shall go with
                the name.";
            attribute :>> criterion = "In a job with a 32 KiB limit, shared mappings
                of one file are refused ENOMEM before the limit is passed while a
                sibling job maps one; with them unmapped every byte charged has come
                back.";
            attribute :>> parent = "H.QUOTA.7";
            attribute :>> unit = "user::vmo::Vmo::attach";
        }
        requirement <'L.user.36'> coherentOnlyWhileUnmapped : ItemLowLevel {
            attribute :>> statement = "Vmo::make_coherent shall be refused while any
                address space maps the object, and once none does shall mark it so
                that Vmo::is_coherent says so.";
            attribute :>> criterion = "A 1-page object mapped shared in a space is
                refused make_coherent; unmapped, make_coherent succeeds and
                is_coherent is true.";
            attribute :>> parent = "H.DMA.3";
            attribute :>> unit = ("user::vmo::Vmo::make_coherent",
                "user::vmo::Vmo::is_coherent", "user::vmo::Vmo::detach");
        }
        requirement <'L.user.37'> aFaultFillsFromTheFile : ItemLowLevel {
            attribute :>> statement = "Vmo::fill_for_fault shall have an object made
                over a file's source fill an absent page from the file before a
                fault commits it, the pages filled going in through
                Vmo::insert_absent, so that a mapping shows the file's bytes, never
                zeros in their place.";
            attribute :>> criterion = "Through a 64-page object over a page source
                mapped shared and privately (check_a_mapping_faults_in_its_source's
                setup), a read of page 5 through the shared mapping returns the
                source's byte after 1 call to the source, with 32 pages committed; a
                private write to page 50, which nothing had read, reads back beside
                the source's next byte, and the object's own page 50 still holds the
                source's bytes. And with kernel objects alone, on every profile, the `core mem` line (user/rehome_check.rs::check_a_fault_fills_from_the_source).";
            attribute :>> parent = "H.MEM.8";
            attribute :>> unit = ("user::vmo::Vmo::fill_for_fault",
                "user::vmo::Vmo::new_filled", "user::vmo::Vmo::insert_absent",
                "user::vmo::Vmo::fill_one_page");
        }
        requirement <'L.user.38'> insertAbsentKeepsWhatIsThere : ItemLowLevel {
            attribute :>> statement = "Vmo::insert_absent shall put a frame in a page
                only if the page is inside the object and holds nothing, and
                otherwise, or with no memory to record it, leave the frame with the
                caller.";
            attribute :>> criterion = "Of a 2-page object with page 0 committed,
                insert_absent of page 0, of page 2 and of page 1 with every
                allocation failing each answers false and page 0 keeps its frame; of
                page 1 it answers true and the object names the frame there; every
                frame refused is freed by the caller's release, 0 frames kept.";
            attribute :>> parent = "H.MEM.9";
            attribute :>> unit = "user::vmo::Vmo::insert_absent";
        }
        requirement <'L.user.39'> pagesPastTheFileEndAreRefused : ItemLowLevel {
            attribute :>> statement = "Once Vmo::set_file_len has lowered the end of
                the file an object holds, a fault through a shared or a private
                mapping of it shall commit and reach no page wholly past that end,
                a page a private mapping copied included.";
            attribute :>> criterion = "A tmpfs file mapped shared and privately over
                4 pages, the private mapping having copied pages 0 and 1
                (check_a_shared_file_mapping's earlier steps), truncated to one
                page: page 0 still reads through the shared mapping, and each of the
                other 3 pages is refused through the shared mapping and through the
                private one, 3 of 3 each. And with kernel objects alone, on every profile, the `core mem` line (user/rehome_check.rs::check_a_cut_file_refuses_past_its_end).";
            attribute :>> parent = "H.TRAP.4";
            attribute :>> unit = ("user::vmo::Vmo::set_file_len",
                "user::vmo::Vmo::past_file_end", "user::vmo::Vmo::commit_within",
                "user::vmo::Vmo::decommit_from", "user::vmo::Vmo::cut_mappings");
        }
        requirement <'L.user.40'> aCutTakesThePrivateCopies : ItemLowLevel {
            attribute :>> statement = "Vmo::cut_mappings shall take every mapping of
                the object's pages from a cut down, and give back the copies private
                mappings made of them once no processor can reach them, so that a
                file grown again shows zeros there through every mapping.";
            attribute :>> criterion = "The file of L.user.39's criterion grown back
                to two pages reads 4096 zero bytes at page 1 through the shared
                mapping and through the private mapping that had copied it. And with kernel objects alone, on every profile, the `core mem` line (user/rehome_check.rs::check_a_file_grown_back_shows_zeros).";
            attribute :>> parent = "H.MEM.6";
            attribute :>> unit = ("user::vmo::Vmo::cut_mappings",
                "user::vmo::Vmo::retire_runs", "user::vmo::forget_together",
                "user::vmo::Vmo::forget_one_at_a_time",
                "user::vmo::ShadowCopies::finish", "user::vmo::Vmo::decommit_from",
                "user::vmo::Vmo::commit_within");
        }
        requirement <'L.user.41'> aTruncationTakesTheFilesPages : ItemLowLevel {
            attribute :>> statement = "Vmo::decommit_from shall give back every
                committed page from its first page on that is not held, so that a
                file truncated and grown again reads zeros there, never its old
                bytes.";
            attribute :>> criterion = "A tmpfs file of 3 pages and 123 bytes,
                truncated into its second page and grown back, reads its first page
                and 10 bytes as written and 0 in every byte after. And with kernel objects alone, on every profile, the `core mem` line (user/rehome_check.rs::check_decommit_from).";
            attribute :>> parent = "H.MEM.6";
            attribute :>> unit = ("user::vmo::Vmo::decommit_from",
                "user::vmo::Vmo::decommit_range", "user::vmo::Vmo::take_range",
                "user::vmo::Pages::take_into", "user::vmo::Vmo::read_page");
        }
        requirement <'L.user.42'> theWriteSealCountsWritableMappings : ItemLowLevel {
            attribute :>> statement = "Vmo::raise_shared_may_write and
                Vmo::lower_shared_may_write shall count the shared mappings that may
                write the file an object holds, a fork child's copies included, so
                that Vmo::writably_mapped says whether any is left.";
            attribute :>> criterion = "F_SEAL_WRITE on a memfd is refused EBUSY
                while a writable shared mapping of it lives, refused EBUSY again
                while only a fork child's copy of that mapping does, and accepted
                once neither does. And with kernel objects alone, on every profile, the `core mem` line (user/rehome_check.rs::check_the_may_write_count).";
            attribute :>> parent = "H.MEM.8";
            attribute :>> unit = ("user::vmo::Vmo::raise_shared_may_write",
                "user::vmo::Vmo::lower_shared_may_write",
                "user::vmo::Vmo::writably_mapped");
        }
        requirement <'L.user.43'> mappedWritesAreReported : ItemLowLevel {
            attribute :>> statement = "For an object with no source (K3b: a disk file's keeps a page's state), Vmo::take_mapped_writes shall report every
                page the object holds while a shared mapping that may write has
                been made since the last report or still lives, none otherwise, and
                on running out of memory keep the mark so that the next report
                names them.";
            attribute :>> criterion = "Of an object with 3 pages committed: before
                any writable shared mapping, a report names 0 pages; with one made
                and gone, the next names 3 and the one after 0; with one alive,
                every report names 3; a report refused for memory is followed by one
                naming 3.";
            attribute :>> parent = "H.MEM.8";
            attribute :>> unit = ("user::vmo::Vmo::take_mapped_writes",
                "user::vmo::Vmo::raise_shared_may_write",
                "user::vmo::Vmo::writably_mapped");
        }
    }

    package AddressSpaces {
        doc /* src/kernel/src/user/space.rs: a process's address space -- the region
             * map and the page tables under it, the mappings of VMOs, files,
             * devices and windows, demand faults and copy-on-write, protect,
             * unmap, mremap and madvise, and the shootdown every takedown of a
             * translation runs before anything it reached is given back. */

        // --- Making a space, and what it refuses before anything is mapped ---

        requirement <'L.user.44'> anEmptySpaceHasARootAndNoRegions : ItemLowLevel {
            attribute :>> statement = "AddressSpace::new shall make a space holding no
                region, with its root table in a page-aligned frame.";
            attribute :>> criterion = "A fresh space holds 0 regions, and its root
                table's physical address is non-zero and a multiple of the page
                size.";
            attribute :>> parent = "H.MEM.1";
            attribute :>> unit = "user::space::AddressSpace::new";
        }
        requirement <'L.user.45'> nothingIsMappedBelowTheFloor : ItemLowLevel {
            attribute :>> statement = "AddressSpace::new shall make a space whose map
                places no region below MMAP_MIN_ADDR, 64 KiB, whether asked for a fixed
                address or given a hint, and lets a region start at the floor
                itself.";
            attribute :>> criterion = "map_anonymous at address 0 is refused; an
                mmap hinted at 0x10 is placed at or above 64 KiB; a MAP_FIXED mmap at
                64 KiB lands there. And with kernel objects alone, on every profile, the `core mem` line (user/rehome_check.rs::check_the_floor).";
            attribute :>> parent = "H.MEM.3";
            attribute :>> unit = ("user::space::AddressSpace::new",
                "user::space::AddressSpace::map_anonymous",
                "user::space::AddressSpace::map_anywhere");
        }
        requirement <'L.user.46'> aRegionOutsideTheUserHalfIsRefused : ItemLowLevel {
            attribute :>> statement = "map_anonymous shall refuse a range outside the
                user half with NotUserRange and insert nothing.";
            attribute :>> criterion = "A one-page mapping at the kernel half's base is
                refused NotUserRange, and the space still holds 0 regions.";
            attribute :>> parent = "H.MEM.2";
            attribute :>> unit = "user::space::AddressSpace::map_anonymous";
        }
        requirement <'L.user.47'> theKernelImageIsNoDeviceMemory : ItemLowLevel {
            attribute :>> statement = "map_device and map_window shall refuse a
                physical range that touches the kernel's image with Refused, whatever
                the caller holds, and insert nothing.";
            attribute :>> criterion = "A device mapping of the image's first page and
                a window of two pages straddling the image's start are each refused
                Refused, and the space holds 0 regions after both.";
            attribute :>> parent = "H.MEM.10";
            attribute :>> unit = ("user::space::check_device_range",
                "user::space::AddressSpace::map_device",
                "user::space::AddressSpace::map_window");
        }
        requirement <'L.user.48'> aDeviceRangeThatWrapsIsABadRange : ItemLowLevel {
            attribute :>> statement = "map_device and map_window shall refuse a
                physical range that wraps the address space with BadRange, before any
                other test, and insert nothing.";
            attribute :>> criterion = "The top page, and a whole-pages length from a
                low page that runs past the top, are each refused BadRange by
                map_device and by map_window, 4 of 4, and the space holds 0 regions.";
            attribute :>> parent = "H.MEM.10";
            attribute :>> unit = ("user::space::check_device_range",
                "user::space::AddressSpace::map_device",
                "user::space::AddressSpace::map_window");
        }
        requirement <'L.user.49'> aDeviceMappingIsWholePagesInTheUserHalf : ItemLowLevel {
            attribute :>> statement = "map_device shall refuse a length that is not
                whole pages with BadRange and a range reaching past the user half
                with NotUserRange.";
            attribute :>> criterion = "Device mappings of no length and of half a page
                are refused BadRange, and one of two pages from the user half's last
                page is refused NotUserRange at that address: 3 refusals of 3.";
            attribute :>> parent = "H.MEM.2";
            attribute :>> unit = ("user::space::check_device_range",
                "user::space::AddressSpace::map_device");
        }
        requirement <'L.user.50'> eachMappingCallRefusesWhatIsItsToRefuse : ItemLowLevel {
            attribute :>> statement = "map_anywhere shall refuse a length of zero,
                map_object an executable mapping and a range past the user half,
                map_file an offset that is not whole pages, and protect a range past
                the user half, each with its own error.";
            attribute :>> criterion = "map_anywhere of no length is BadRange;
                map_object executable is Refused and past the user half NotUserRange;
                map_file from half a page in is BadRange; protect of two pages from
                the user half's last page is NotUserRange: 5 refusals of 5.";
            attribute :>> parent = ("H.MEM.2", "H.MEM.18");
            attribute :>> unit = ("user::space::AddressSpace::map_anywhere",
                "user::space::AddressSpace::map_object",
                "user::space::AddressSpace::map_file",
                "user::space::AddressSpace::protect");
        }

        // --- Faults ---

        requirement <'L.user.51'> aFaultOutsideEveryRegionIsASegfault : ItemLowLevel {
            attribute :>> statement = "fault shall answer an address no region covers
                with NotMapped, which the process receives as SIGSEGV.";
            attribute :>> criterion = "A read fault at the first address past a
                two-page region is answered NotMapped.";
            attribute :>> parent = "H.MEM.1";
            attribute :>> unit = ("user::space::AddressSpace::fault",
                "user::space::AddressSpace::fill_file_page",
                "user::space::AddressSpace::resolve",
                "user::space::SpaceError::fmt");
        }
        requirement <'L.user.52'> aWriteToAReadOnlyRegionIsRefused : ItemLowLevel {
            attribute :>> statement = "fault shall refuse a write to a region that does
                not permit writing with Refused, and resolve a read of it.";
            attribute :>> criterion = "In a read-only region a write fault is answered
                Refused and a read fault at the same address succeeds.";
            attribute :>> parent = "H.MEM.1";
            attribute :>> unit = ("user::space::AddressSpace::fault",
                "user::space::AddressSpace::resolve", "user::space::permits");
        }
        requirement <'L.user.53'> anInaccessibleRegionIsNeverMapped : ItemLowLevel {
            attribute :>> statement = "fault shall refuse a read of a region that
                permits nothing with Refused and install no translation for it.";
            attribute :>> criterion = "A read fault in a PROT_NONE region is answered
                Refused, and the page does not translate in the space's tables
                afterwards.";
            attribute :>> parent = "H.MEM.1";
            attribute :>> unit = ("user::space::AddressSpace::fault",
                "user::space::AddressSpace::resolve", "user::space::permits");
        }
        requirement <'L.user.54'> pagesArriveOnDemandAndGoBack : ItemLowLevel {
            attribute :>> statement = "An anonymous mapping shall commit no frame until
                a page is faulted, each fault shall map the faulting page and no
                other, an unmap shall give back the pages of its range and leave the
                rest mapped, and dropping the space shall give back every frame it
                held.";
            attribute :>> criterion = "Mapping 4 pages costs exactly 1 frame, the root;
                faulted out of order, each of the 4 translates and holds what is
                written to it; re-faulting a present page costs 0 frames; unmapping
                the first 2 gives back at least 2 frames, page 0 no longer translates
                and page 2 still does; with the space dropped the free count is what
                it was before, 0 frames kept.";
            attribute :>> parent = ("H.MEM.1", "H.MEM.9");
            attribute :>> unit = ("user::space::AddressSpace::map_anonymous",
                "user::space::AddressSpace::add_region", "user::space::sharing_of",
                "user::space::AddressSpace::fault",
                "user::space::AddressSpace::resolve", "user::space::commit_page",
                "user::space::AddressSpace::unmap",
                "user::space::AddressSpace::take_down",
                "user::space::AddressSpace::give_back", "user::space::owner",
                "user::space::note", "user::space::AddressSpace::drop_unnamed",
                "user::space::drop_objects", "user::space::AddressSpace::drop");
        }

        // --- A space on a processor ---

        requirement <'L.user.55'> theProcessorWalksAnInstalledSpace : ItemLowLevel {
            attribute :>> statement = "install shall make the running processor
                translate user addresses through the space's own tables, on the
                first installation and on every one after an uninstall.";
            attribute :>> criterion = "Over 2 rounds of install, use and uninstall, a
                write through each of 2 user addresses reads back through the address
                and through the direct map's alias of the frame the space's tables
                name, for both pages in both rounds; and the space dropped keeps 0
                frames.";
            attribute :>> parent = "H.MEM.1";
            attribute :>> unit = ("user::space::AddressSpace::install",
                "user::space::AddressSpace::uninstall",
                "user::space::this_logical_cpu");
        }
        requirement <'L.user.56'> twoSpacesReadTheirOwnPageAtOneAddress : ItemLowLevel {
            attribute :>> statement = "install and uninstall, as the scheduler calls
                them, shall leave a task reading its own space's frame at a user
                address however often one processor alternates between two spaces.";
            attribute :>> criterion = "Two tasks pinned to one processor, each in a
                space holding a different value at one address, yield between reads:
                128 reads of 128 return the reader's own value and 0 the other's (the
                `spaces` line), and the spaces dropped keep 0 frames.";
            attribute :>> parent = "H.MEM.1";
            attribute :>> unit = ("user::space::AddressSpace::install",
                "user::space::AddressSpace::uninstall",
                "user::space::this_logical_cpu");
        }

        // --- fork and copy-on-write ---

        requirement <'L.user.57'> aSharedRegionIsOneObjectAcrossFork : ItemLowLevel {
            attribute :>> statement = "fork shall give the child the same object for a
                MAP_SHARED region, not a copy, so that the two spaces reach one frame
                with one holder and see each other's writes.";
            attribute :>> criterion = "After a fork of a space holding a written
                shared page, the child's write fault maps the parent's frame, the
                frame has 1 holder, a write through the child's frame reads back
                through the parent's, and the spaces dropped keep 0 frames.";
            attribute :>> parent = "H.MEM.16";
            attribute :>> unit = ("user::space::AddressSpace::fork",
                "user::space::shared_object", "user::space::attach_child",
                "user::space::sharing_of");
        }
        requirement <'L.user.58'> forkSharesAndAWriteCopies : ItemLowLevel {
            attribute :>> statement = "fork shall take the write permission away
                from the parent's translations of its private writable pages,
                leaving them on the same frames, and share those frames with the
                child, and a write to a page some other space
                still holds shall copy it into a frame of the writer's own, while a
                write to a page nobody else holds any more shall copy nothing.";
            attribute :>> criterion = "After a fork of 2 written private pages the
                parent translates both to their original frames and neither
                writably; read faults leave both sides on the
                original frames with 2 holders each; the child's write, made with
                its space installed, lands in a new frame of 1 holder, leaves the
                original at 1 holder with the parent's value, and a second write
                copies nothing; with the parent dropped the child's write to the
                other page keeps its frame and contents; 0 frames kept.";
            attribute :>> parent = ("H.MEM.8", "H.MEM.9");
            attribute :>> unit = ("user::space::AddressSpace::fork",
                "user::space::AddressSpace::protect_copied_on_write",
                "user::space::inherited", "user::space::attach_child",
                "user::space::AddressSpace::begin_shootdown",
                "user::space::AddressSpace::shoot",
                "user::space::AddressSpace::resolve", "user::space::copy_on_write",
                "user::space::AddressSpace::forget_in", "mm::write_protect_in");
        }
        requirement <'L.user.229'> aSoleHoldersWriteReusesThePage : ItemLowLevel {
            attribute :>> statement = "A copy-on-write write fault whose space holds
                the page alone shall make its present read-only translation
                writable in place, on the same frame, beginning no shootdown.";
            attribute :>> criterion = "After a fork of a written private page and
                of a private file mapping's copied page, and the child's drop, the
                parent's write fault to each leaves the same frame translated,
                writable, at 1 holder, with shootdowns_begun unchanged; a write
                through the parent's own address, made with its space installed
                after a read through it cached the read-only translation,
                reaches that frame; 0 frames kept.";
            attribute :>> parent = ("H.MEM.8", "H.MEM.9");
            attribute :>> unit = ("user::space::AddressSpace::write_copy_on_write",
                "user::space::AddressSpace::write_shadow_copy_on_write",
                "user::space::reusable_in_place", "mm::allow_write_in");
        }
        requirement <'L.user.235'> aSoleHoldersWriteToAnUnmappedPageMapsIt : ItemLowLevel {
            attribute :>> statement = "A copy-on-write write fault to a page its
                space holds alone, with no translation at the faulting address,
                shall map the page writable on the frame the object names,
                beginning no shootdown.";
            attribute :>> criterion = "In a reserve made writable by protect, the
                first write fault to a page leaves it translated, writable, at 1
                holder, with shootdowns_begun unchanged, and a write through the
                space's own address, made with the space installed, reaches the
                frame; after protect to read-only and back to writable, which
                leaves no translation, the next write fault leaves the same frame
                translated, writable, at 1 holder, with shootdowns_begun
                unchanged, and a write through the address reaches it; 0 frames
                kept.";
            attribute :>> parent = ("H.MEM.8", "H.MEM.9");
            attribute :>> unit = "user::space::AddressSpace::write_copy_on_write";
        }
        requirement <'L.user.59'> aKernelWriteToAnOwnPageTakesNothingDown : ItemLowLevel {
            attribute :>> statement = "with_page shall let a write go straight through
                to a copy-on-write page this space alone holds, taking no translation
                down.";
            attribute :>> criterion = "A kernel write through with_page to a page the
                child has already copied succeeds and begins 0 shootdowns of the
                child's space.";
            attribute :>> parent = "H.MEM.8";
            attribute :>> unit = ("user::space::AddressSpace::with_page",
                "user::space::writable_in_place");
        }
        requirement <'L.user.60'> aPageMadeWritableAfterForkIsCopied : ItemLowLevel {
            attribute :>> statement = "A private page read-only at a fork and made
                writable afterwards with protect shall be copied by the side that
                writes it, the other keeping its own.";
            attribute :>> criterion = "A page written, protected read-only, forked and
                protected writable in the child is copied by the child's installed
                write: the child's frame differs from the parent's, holds the
                child's value, the parent's holds its own, and 0 frames are kept.";
            attribute :>> parent = "H.MEM.8";
            attribute :>> unit = ("user::space::AddressSpace::protect",
                "user::space::AddressSpace::resolve", "user::space::copy_on_write");
        }
        requirement <'L.user.128'> protectKeepsAMappingShared : ItemLowLevel {
            attribute :>> statement = "protect shall change a region's read, write
                and execute permissions and keep whether it is shared.";
            attribute :>> criterion = "A memfd mapped shared and read-write and
                protected read-write again is written through the mapping: the
                byte is in the file (the memfd line). And with kernel objects alone, on every profile, the `core mem` line (user/rehome_check.rs::check_protect_keeps_shared).";
            attribute :>> parent = "H.MEM.16";
            attribute :>> unit = "user::space::AddressSpace::protect";
        }
        requirement <'L.user.129'> aWritableRegionReads : ItemLowLevel {
            attribute :>> statement = "fault shall permit a read of a region that
                permits writing, as Linux's protection_map makes a PROT_WRITE
                mapping readable, and still refuse a read of one that permits
                nothing.";
            attribute :>> criterion = "A memfd's page mapped shared with PROT_WRITE
                alone reads what the file holds (the memfd line), while a read
                of a PROT_NONE region is still refused (L.user.53). And with kernel objects alone, on every profile, the `core mem` line (user/rehome_check.rs::check_a_write_only_region_reads).";
            attribute :>> parent = "H.MEM.1";
            attribute :>> unit = ("user::space::AddressSpace::fault",
                "user::space::permits");
        }
        requirement <'L.user.61'> aProgramsCopyOnWriteWriteIsItsOwn : ItemLowLevel {
            attribute :>> statement = "A write by a program's own instruction to a
                private page its fork or clone still shares shall be copied for the side that
                wrote it and be seen by neither the other side nor the page.";
            attribute :>> criterion = "The `cow` program, whose parent and child each
                write a page both shared after the fork, exits 61 (the `cow` line). On Bare, present and desktop (bare_side_check): two Bares on a space and its clone, each a program's own store, a_store_copies_for_the_side_that_writes, which replaces the `cow` line in user builds once a caller is built there (6110 (1), (7)).";
            attribute :>> parent = "H.MEM.8";
            attribute :>> unit = ("user::space::AddressSpace::fork",
                "user::space::AddressSpace::resolve", "user::space::copy_on_write",
                "user::space::AddressSpace::forget_in",
                "user::space::AddressSpace::begin_shootdown",
                "user::space::AddressSpace::shoot");
        }
        requirement <'L.user.62'> aProgramsSharedWriteReachesItsParent : ItemLowLevel {
            attribute :>> statement = "A forked or cloned program's write to a MAP_SHARED
                anonymous page shall reach its parent, a page the child faults in
                first included, and its write to a MAP_PRIVATE page shall not.";
            attribute :>> criterion = "The `shared` program exits 62 (the `shared`
                line). On Bare, present and desktop (bare_side_check): a clone's own stores to two shared pages and a private one, a_shared_store_reaches_the_other_side; the `shared` program is the load's.";
            attribute :>> parent = "H.MEM.16";
            attribute :>> unit = ("user::space::AddressSpace::fork",
                "user::space::attach_child", "user::space::shared_object",
                "user::space::AddressSpace::resolve", "user::space::commit_page");
        }

        // --- Reaching user memory from the kernel ---

        requirement <'L.user.63'> anUnmapWaitsForACopyHoldingItsPage : ItemLowLevel {
            attribute :>> statement = "with_page shall hold the page it translated for
                as long as its copy runs, so that an unmap of the page on another
                processor does not return before the copy ends.";
            attribute :>> criterion = "On a machine with two processors or more, a
                copy holding a page in with_page on one processor for 30 ms reads the
                page's byte, the unmap started on the other while it held had not
                returned when the copy ended, and it had returned once both tasks
                were gone (the `unmap` line).";
            attribute :>> parent = "H.MEM.17";
            attribute :>> unit = ("user::space::AddressSpace::with_page",
                "user::space::AddressSpace::unmap");
        }
        requirement <'L.user.64'> aLookupRefusesAWriteToAReadOnlyRegion : ItemLowLevel {
            attribute :>> statement = "with_present_page shall refuse a write in a
                region that does not permit writing with Refused.";
            attribute :>> criterion = "with_present_page asked to write in a read-only
                region is answered Refused at that address.";
            attribute :>> parent = "H.MEM.1";
            attribute :>> unit = ("user::space::AddressSpace::with_present_page",
                "user::space::permits");
        }
        requirement <'L.user.65'> aLookupUnderALockNeverFaults : ItemLowLevel {
            attribute :>> statement = "with_present_page shall run nothing and answer
                that the page must be faulted first when the page is absent or, for a
                write, a copy-on-write page another space still holds or a private
                file mapping's page its shadow does not hold.";
            attribute :>> criterion = "with_present_page answers Ok(None), and its
                closure is not run, for an absent page, a write to a page a fork
                still shares, and a write to a file page a private mapping has only
                read; after a fault each answers Some.";
            attribute :>> parent = "H.MEM.8";
            attribute :>> unit = ("user::space::AddressSpace::with_present_page",
                "user::space::writable_in_place");
        }

        // --- Device memory and windows ---

        requirement <'L.user.66'> aWindowIsRefusedAsDeviceMemoryIs : ItemLowLevel {
            attribute :>> statement = "map_window shall refuse an executable window
                with Refused, a length that is not whole pages with BadRange and a
                range reaching past the user half with NotUserRange.";
            attribute :>> criterion = "A window over a frame asked read-execute is
                Refused, of half a page BadRange, and of two pages from the user
                half's last page NotUserRange: 3 refusals of 3.";
            attribute :>> parent = ("H.MEM.2", "H.MEM.18");
            attribute :>> unit = ("user::space::AddressSpace::map_window",
                "user::space::AddressSpace::map_window_typed",
                "user::space::check_device_range");
        }
        requirement <'L.user.67'> aWindowKeepsItsKeeperWhileMapped : ItemLowLevel {
            attribute :>> statement = "A window's region shall keep what map_window was
                given to keep until no region names the window, and an unmap of
                another mapping shall let go of that mapping's file and not of the
                window's keeper.";
            attribute :>> criterion = "Mapped, the window holds its keeper (count 2)
                and is the highest mapping; a file mapping beside it unmapped leaves
                its open file at count 1 and the keeper at 2; the window unmapped
                leaves the keeper at 1.";
            attribute :>> parent = "H.MEM.9";
            attribute :>> unit = ("user::space::AddressSpace::map_window",
                "user::space::AddressSpace::unmap",
                "user::space::AddressSpace::give_back",
                "user::space::AddressSpace::drop_unnamed", "user::space::still_named",
                "user::space::naming", "user::space::Named::of",
                "user::space::Named::contains", "user::space::drop_objects",
                "user::space::touched_ids", "user::space::all_still_named");
        }
        requirement <'L.user.68'> aDeviceMappingReachesTheDevicesOwnPages : ItemLowLevel {
            attribute :>> statement = "A page of a device region shall be faulted in to
                the device's own physical page, in the space that mapped it and in a
                fork child of it alike.";
            attribute :>> criterion = "On a machine with a whole-page aperture,
                io_mapping_map's address, faulted, translates to the aperture's
                physical address in the process's space and in a fork child's.";
            attribute :>> parent = ("H.MEM.1", "H.DMA.5");
            attribute :>> unit = ("user::space::AddressSpace::map_device",
                "user::space::AddressSpace::fault_device",
                "user::space::AddressSpace::resolve",
                "user::space::AddressSpace::fork");
        }
        requirement <'L.user.108'> aPrefetchableApertureMapsWriteCombining : ItemLowLevel {
            attribute :>> statement = "io_mapping_map_combining shall map an
                aperture the device says is prefetchable write-combining, its pages
                faulted in to the device's own memory, and shall refuse an aperture
                of registers with INVALID_ARGS; on x86-64 it shall refuse every
                aperture with INVALID_ARGS unless every processor programmed its
                PAT with the write-combining entry.";
            attribute :>> criterion = "On x86-64, AArch64 and ARMv7-A -- each of
                whose test-boot machines has a virtio-pci function with a whole-page
                prefetchable aperture, the boot's handles line saying 1 mapped
                write-combining -- its write-combining mapping reaches the
                aperture's physical address and its page table entry reads
                write-combining (normal non-cacheable on the two Arm
                architectures), not device; a register aperture's is refused with
                INVALID_ARGS; on x86-64, with one processor's PAT counted as not
                programmed, the prefetchable aperture's is refused with
                INVALID_ARGS, and with that refusal dropped stage 9 fails naming
                it.";
            attribute :>> parent = ("H.MEM.1", "H.DMA.5");
            attribute :>> unit = ("syscall::native::io_mapping_map",
                "object::io_mapping::IoMapping::map_into",
                "object::io_mapping::IoMapping::prefetchable",
                "object::io_mapping::combining_ready",
                "object::io_mapping::count_one_unprogrammed_for_check",
                "user::space::AddressSpace::map_device",
                "user::space::AddressSpace::fault_device", "mm::flags_in");
        }
        requirement <'L.user.109'> oneMemoryTypePerDevicePage : ItemLowLevel {
            attribute :>> statement = "A page of device memory shall be mapped into
                user address spaces with one memory type at a time: map_device and
                map_window shall refuse a range any page of which a live user
                mapping holds as another of device, write-combining or cached with
                OtherMemoryType -- ALREADY_BOUND from io_mapping_map and
                io_mapping_map_combining, EINVAL from mmap of a render node's blob
                -- and a mapping's hold shall end only once no region of any
                address space maps it, after its unmap's shootdown has returned.
                Holds shall be counted in one claim per distinct range and type, an
                I/O mapping's range being its whole aperture and a window's its
                whole blob, so that no number of mappings adds a claim.";
            attribute :>> criterion = "On x86-64, AArch64 and ARMv7-A, with a
                prefetchable aperture mapped write-combining, io_mapping_map of it is
                ALREADY_BOUND and a cached window over it is OtherMemoryType; with
                it mapped as a cached window, and then uncached, after the
                write-combining mapping is unmapped, io_mapping_map_combining is
                ALREADY_BOUND; with every mapping of it unmapped it maps
                write-combining again; mapping the cached window again, whole and
                one page of it, leaves the number of claims unchanged; with the
                type comparison dropped from memory_type::hold, stage 9 fails
                naming the uncached mapping made beside the write-combining one,
                and with every hold given a claim of its own it fails naming the
                claim the window's second mapping made.";
            attribute :>> parent = ("H.MEM.1", "H.DMA.5");
            attribute :>> unit = ("user::memory_type::hold",
                "user::memory_type::MemoryType::of",
                "user::space::hold_type",
                "user::space::AddressSpace::map_device",
                "user::space::AddressSpace::map_window",
                "user::space::AddressSpace::give_back",
                "user::memory_type::Hold::drop", "user::memory_type::release",
                "user::memory_type::claims", "user::space::WindowPages::all",
                "user::space::WindowPages::check");
        }
        requirement <'L.user.126'> onlyPlainMemoryIsAnonymous : ItemLowLevel {
            attribute :>> statement = "Vmo::is_anonymous shall answer true for a
                VMO iff it has no filler and no file bound: plain anonymous
                memory, never a file's object on a disk or in memory, so that
                what asks it -- a chardev driver's dmabuf install -- refuses a
                file's VMO with INVALID_ARGS.";
            attribute :>> criterion = "In stage 10's chardev self-check, a
                dmabuf install of a memfd's VMO, its handle holding READ, WRITE,
                MAP and TRANSFER, is refused INVALID_ARGS, and one of a VMO from
                vmo_create is installed; with is_anonymous answering true for
                every VMO, stage 10 fails naming the memfd's dmabuf. And with kernel objects alone, on every profile, the `core mem` line (user/rehome_check.rs::check_is_anonymous).";
            attribute :>> parent = "H.MEM.1";
            attribute :>> unit = "user::vmo::Vmo::is_anonymous";
        }
        requirement <'L.user.132'> onlyTheDriversOwnVmoCombines : ItemLowLevel {
            doc /* K6 of docs/INTEL-GPU.md section 5; the consultant's K6 (1),
                 * ledger 2026-10-18 line 2352. A chardev driver answers a
                 * program's mmap with MAP_VMO | MAP_WRITE_COMBINING, naming a
                 * VMO of its own handle table (map_reply, load ring), and the
                 * item decides whether that VMO may be write-combining at all.
                 * x86-64 alone at first: each Arm architecture's attribute
                 * (normal non-cacheable) is still to be argued, so there the
                 * answer is refused as it was before K6. */
            attribute :>> statement = "Vmo::make_combining shall make a VMO
                write-combining for every user mapping from then on only on
                x86-64, where the processor has CLFLUSH and every processor
                programmed its PAT with the write-combining entry, and only for
                plain anonymous memory that is not coherent and that no address
                space maps; anywhere else, and for any other VMO, it shall
                refuse and leave the VMO as it was.";
            attribute :>> criterion = "Stage 10's chardev check: on x86-64 the
                driver's own anonymous VMO answered MAP_VMO with
                MAP_WRITE_COMBINING is made write-combining; on AArch64 and
                ARMv7-A the same answer is refused, the program's mmap EIO and
                the VMO unchanged; on every machine a memfd's VMO and a VMO an
                address space already maps are refused the same way. With the
                anonymous test or the mappers' test dropped, the boot panics. And with kernel objects alone, on every profile, the `core mem` line (user/rehome_check.rs::check_make_combining).";
            attribute :>> parent = ("H.MEM.1", "H.MEM.15");
            attribute :>> unit = ("user::vmo::Vmo::make_combining",
                "user::vmo::Vmo::is_combining", "arch::x86_64::framebuffer::user_combining");
        }
        requirement <'L.user.133'> aCombiningVmoIsOneTypeToPrograms : ItemLowLevel {
            doc /* The memory-type aliasing argument (the consultant's K6 (2),
                 * and ledger 2368 (1)-(3)). A write-combining VMO's frames
                 * stay write-back in the kernel's direct map, as i915 keeps an
                 * LLC part's objects while a program maps them
                 * write-combining. The SDM (Vol. 3A 11.12.4) makes that safe
                 * only if no write-back line of the page is left to be
                 * evicted over what write-combining stores put in memory, and
                 * no read through the write-back alias hits a stale line.
                 *
                 * (1) Every user mapping of the VMO, in every space, is
                 * write-combining, never also write-back beside it:
                 * AddressSpace::resolve, and typed() for a private mapping's
                 * read of the page.
                 * (2) Every path that reaches one of its frames through the
                 * direct map is flushed, refused or unreachable:
                 * - zeroing a new frame (Vmo::commit, Vmo::commit_run):
                 *   flushed after, under the pages' lock; the frames there
                 *   when make_combining sets the flag: flushed by it;
                 * - uaccess, so every syscall buffer, futex word and
                 *   put_user in such a page (AddressSpace::with_page,
                 *   with_present_page): coherent_touch flushes the page's
                 *   lines before the copy and after it, where this space maps
                 *   the page write-combining;
                 * - Vmo::read_present, read_page, write_page,
                 *   commit_and_write and zero_from: flushed before a read
                 *   and after a write;
                 * - vmo_read and vmo_write: refused BAD_STATE;
                 * - a private mapping's copy of the page (copy_or_zero):
                 *   flushed before the copy;
                 * - the quarantine's fold of a dead driver's pinned frame
                 *   (object::pin::fold): flushed before;
                 * - a block or net ring, an audio buffer, a display card's
                 *   buffer, which a kernel core reads and writes for its life:
                 *   marked by Vmo::take_kernel_view, which make_combining
                 *   then refuses, and which refuses an object already
                 *   write-combining, so the two never meet;
                 * - copy-on-write copies of a shared frame (copy_on_write,
                 *   Pages::exclusive, fork_private's copy of a held page):
                 *   unreachable, since a write-combining VMO is mapped only
                 *   shared and never forked into a private object;
                 * - a core dump, /proc/<pid>/mem and process_vm_readv: not
                 *   built.
                 * Drain before reuse, by code: a frame of the VMO goes back
                 * only after AddressSpace::begin_shootdown's set of
                 * processors has answered smp::flush_tlb_pages (each one
                 * interrupted and running INVLPG, waited for in
                 * invalidate_pages); a processor leaves a space's set only
                 * after AddressSpace::install or uninstall has loaded another
                 * root into CR3, with or without a PCID's flush (docs/PCID.md).
                 * The interrupt, INVLPG and the CR3 load each drain the
                 * write-combining buffers (SDM Vol. 3A 11.3.1), so no buffered
                 * store reaches a frame after it is reused. */
            attribute :>> statement = "Every user mapping of a page of a
                write-combining VMO shall be write-combining; each of its frames
                shall have its cache lines written back and invalidated after
                the kernel zeroed it and before the VMO can be mapped
                write-combining over it; every copy the kernel makes to or from
                such a page through the direct map shall flush the page's lines
                before it and after it; vmo_read and vmo_write of the VMO shall
                be refused BAD_STATE; and no kernel core that reads a VMO
                through the direct map for its life shall take one that is
                write-combining, nor shall one it took become so.";
            attribute :>> criterion = "Stage 10's chardev check on x86-64: a
                program's mapping of the VMO, faulted in by a write, reads back
                write-combining and not device; a write(2) from it and a
                read(2) into it through a memfd round-trip its bytes and count
                four coherent touches; vmo_read of the VMO is BAD_STATE. With
                resolve's write-combining choice, the coherent touch or
                vmo_copy's refusal dropped, the boot panics. The flush's effect
                is argued, since QEMU models no cache. And with kernel objects alone, on every profile, the `item` line (syscall/rehome_check.rs::check_a_combining_object).";
            attribute :>> parent = ("H.MEM.1", "H.MEM.15");
            attribute :>> unit = ("user::vmo::Vmo::commit", "user::vmo::Vmo::commit_run",
                "user::vmo::flush_frame", "user::vmo::Vmo::flush_if_combining",
                "user::vmo::Vmo::take_kernel_view", "user::vmo::Vmo::read_present",
                "user::vmo::Vmo::read_page", "user::vmo::Vmo::write_page",
                "user::vmo::Vmo::commit_and_write", "user::vmo::Vmo::zero_from",
                "user::space::AddressSpace::resolve",
                "user::space::AddressSpace::fault_private_file", "user::space::typed",
                "user::space::AddressSpace::with_page",
                "user::space::AddressSpace::with_present_page",
                "user::space::AddressSpace::coherent_touch", "user::space::copy_or_zero",
                "object::pin::fold", "syscall::native::vmo_copy",
                "arch::x86_64::framebuffer::flush_cache_lines",
                "arch::x86_64::framebuffer::flush_lines");
            attribute :>> scope = "personality=kernel";
        }
        requirement <'L.user.107'> aCopyThroughADevicePageIsRefused : ItemLowLevel {
            attribute :>> statement = "with_page and with_present_page shall refuse
                a copy to or from a page of a device region with Refused, before the
                page is faulted in or a direct-map address is formed for it, and
                shall form one only through direct_map_ram.";
            attribute :>> criterion = "A writev() from and a readv() into a device's
                aperture mapped by io_mapping_map, a cached window past all RAM and,
                where the memory map has a hole between runs of RAM, a window over
                it are each EFAULT with the page still absent, and with_present_page
                refuses each for reading and writing; with the aperture's page
                faulted in, both copies are EFAULT again (the `copies` line).";
            attribute :>> parent = ("H.MEM.1", "H.DMA.5");
            attribute :>> unit = ("user::space::AddressSpace::with_page",
                "user::space::AddressSpace::with_present_page", "user::space::copyable");
        }

        // --- mremap ---

        requirement <'L.user.69'> mremapRefusesWhatItShould : ItemLowLevel {
            attribute :>> statement = "remap shall refuse a new length of zero with
                BadRange, an old range longer than its region with NotMapped and a
                fixed destination overlapping the old range with BadRange, and leave
                a remap to the same length where it is.";
            attribute :>> criterion = "On a two-page region, a remap to length 0 is
                BadRange, of three pages NotMapped, to a fixed address one page in
                BadRange -- 3 refusals of 3 -- and to the same length anywhere
                answers the region's own address.";
            attribute :>> parent = "H.MEM.1";
            attribute :>> unit = ("user::space::AddressSpace::remap",
                "user::space::remap_target", "user::space::user_range");
        }
        requirement <'L.user.70'> aRegionGrowsWhereItHasRoom : ItemLowLevel {
            attribute :>> statement = "remap shall grow a region where it is when the
                pages after it are free, even when it may move.";
            attribute :>> criterion = "A one-page region with free pages after it,
                remapped to three pages anywhere, answers its own address.";
            attribute :>> parent = "H.MEM.1";
            attribute :>> unit = ("user::space::AddressSpace::remap",
                "user::space::remap_target", "user::space::grows_in_place",
                "user::space::AddressSpace::move_private",
                "user::space::AddressSpace::add_fresh",
                "user::space::AddressSpace::remap_backing");
        }
        requirement <'L.user.71'> aSharedRegionNeverGrowsOverItsOwnPages : ItemLowLevel {
            attribute :>> statement = "remap shall refuse with OutOfMemory to grow a
                shared region over offsets of its object that another region of the
                space already names.";
            attribute :>> criterion = "A three-page shared region whose last page was
                moved away on its own cannot grow its first two pages back to three
                in place: OutOfMemory.";
            attribute :>> parent = ("H.MEM.1", "H.MEM.9");
            attribute :>> unit = ("user::space::AddressSpace::remap",
                "user::space::named_elsewhere");
        }
        requirement <'L.user.72'> aHeldPageDoesNotMove : ItemLowLevel {
            attribute :>> statement = "remap shall refuse with OutOfMemory to move a
                private region that holds a page a device holds.";
            attribute :>> criterion = "A written one-page region whose page is held,
                with a neighbour in the way, is refused OutOfMemory when remapped to
                two pages anywhere.";
            attribute :>> parent = "H.DMA.3";
            attribute :>> unit = ("user::space::AddressSpace::remap",
                "user::space::AddressSpace::move_private",
                "user::space::AddressSpace::add_fresh",
                "user::space::AddressSpace::drop_fresh");
        }
        requirement <'L.user.73'> mremapCarriesTheContents : ItemLowLevel {
            attribute :>> statement = "remap shall refuse to grow a region in the way
                of a neighbour unless it may move, and shall carry a region's
                contents with it when it moves it, grow it with zeros and shrink it
                in place, leaving nothing readable where it no longer is.";
            attribute :>> criterion = "Two written pages with a neighbour after them:
                growing to four without MREMAP_MAYMOVE is ENOMEM; with it they move,
                a string in the first page and one across the page boundary read
                back at the new address, the old address is unreadable and the
                fourth page reads 0; shrunk to one page in place it keeps the first
                page's string and its tail is unreadable; moved to the old address
                with MREMAP_FIXED it lands there with the string. And with kernel objects alone, on every profile, the `core mem` line (user/rehome_check.rs::check_remap).";
            attribute :>> parent = ("H.MEM.1", "H.MEM.6");
            attribute :>> unit = ("user::space::AddressSpace::remap",
                "user::space::remap_object", "user::space::remap_target",
                "user::space::grows_in_place", "user::space::user_range",
                "user::space::AddressSpace::move_private",
                "user::space::AddressSpace::add_fresh",
                "user::space::AddressSpace::remap_backing",
                "user::space::AddressSpace::clear_for_remap",
                "user::space::AddressSpace::take_down",
                "user::space::AddressSpace::give_back");
        }

        // --- Native objects and shared code ---

        requirement <'L.user.74'> aNativeRegionIsNotReshaped : ItemLowLevel {
            attribute :>> statement = "protect and remap shall refuse with Refused a
                region vmo_map made, whose protection and size are its handle's.";
            attribute :>> criterion = "A read-only vmo_map region is refused Refused
                by protect to read-write and by remap to two pages: 2 refusals of
                2.";
            attribute :>> parent = "H.OBJ.2";
            attribute :>> unit = ("user::space::AddressSpace::protect",
                "user::space::AddressSpace::remap", "user::space::Inner::reshapeable");
        }
        requirement <'L.user.75'> aMappedVmoIsTheVmo : ItemLowLevel {
            attribute :>> statement = "map_object shall map the object itself, shared,
                so that its bytes and the mapping's are the same bytes, a fork child
                writes into the same object, and the mapping outlives the handle it
                was made with.";
            attribute :>> criterion = "A VMO mapped at the address asked shows bytes
                vmo_write put there; bytes written through the mapping, and through a
                fork child's, are read back by vmo_read or the parent; with every
                handle to the VMO closed the mapping still shows its bytes.";
            attribute :>> parent = "H.MEM.1";
            attribute :>> unit = ("user::space::AddressSpace::map_object",
                "user::space::AddressSpace::add_region",
                "user::space::AddressSpace::fork", "user::space::shared_object",
                "user::space::attach_child");
        }
        requirement <'L.user.76'> theVdsoIsReadAndRunOverReadOnlyData : ItemLowLevel {
            attribute :>> statement = "map_shared_code shall map a two-page object as a
                read-only shared data page below a read-and-run shared code page,
                neither writable nor able to be made writable.";
            attribute :>> criterion = "Where the architecture has a vDSO, a space it
                is mapped into shows the code page read, execute, shared and not
                writable over a data page read, shared and neither, the image reads
                as ELF, and a write through with_page and a protect to read-write
                are each refused on both pages, 4 of 4.";
            attribute :>> parent = "H.MEM.18";
            attribute :>> unit = ("user::space::AddressSpace::map_shared_code",
                "user::space::AddressSpace::map_shared_code_near",
                "user::space::AddressSpace::add_region",
                "user::space::AddressSpace::with_page", "user::space::permits",
                "user::space::AddressSpace::protect");
        }
        // Split from L.user.76 (the consultant's T1, ledger 2026-10-14 line
        // 966): the vDSO view swapped in place for a space entering a time
        // namespace (docs/NAMESPACES.md section 12.1).
        requirement <'L.user.130'> aSharedCodeViewIsReplacedInPlace : ItemLowLevel {
            attribute :>> statement = "replace_shared_code shall give a space
                another two-page shared code object at the place the space maps
                the first, the first unmapped and the new one mapped as
                map_shared_code maps one, leaving every other space's view
                alone.";
            attribute :>> criterion = "A space forked into a time namespace
                that shifts a clock has the shifted object mapped at the first
                one's place and the first unmapped, the parent's mapping
                unchanged, and a grandchild in its parent's namespace keeps its
                parent's view (the `timens` line).";
            attribute :>> parent = "H.MEM.18";
            attribute :>> unit = ("user::space::AddressSpace::replace_shared_code",
                "user::space::AddressSpace::map_shared_code_near");
        }
        requirement <'L.user.131'> theVdsoIsClearOfWinesRange : ItemLowLevel {
            attribute :>> statement = "map_shared_code shall map a two-page object to
                end at the address it is asked for when that range is free; the
                vDSO is asked for 128 MiB below the stack's top, below the stack's
                guard and outside 0x7ffffe000000..0x7fffffff0000, the range Wine's
                x86-64 preloader reserves, so that a program it starts keeps
                AT_SYSINFO_EHDR.";
            attribute :>> criterion = "On x86-64 and AArch64, the architectures with a
                vDSO, a space a program was loaded into as exec loads it maps the vDSO's
                image at exec::VDSO_END less a page, outside Wine's range, with the
                stack's guard the next region above it (the `vdso` line).";
            attribute :>> parent = "H.SCHED.9";
            attribute :>> unit = ("user::space::AddressSpace::map_shared_code",
                "user::space::AddressSpace::map_shared_code_near");
        }
        requirement <'L.user.77'> aSpaceFindsItsTrampoline : ItemLowLevel {
            attribute :>> statement = "shared_code_at shall answer where
                map_shared_code put an object in the space, so that a signal's return
                trampoline is found at its place in the mapped vDSO.";
            attribute :>> criterion = "On an architecture whose vDSO holds only its
                signal return trampoline, a fresh space the vDSO is mapped into finds
                the trampoline at the mapped image plus the trampoline's offset (the
                `vdso` line).";
            attribute :>> parent = "H.TRAP.4";
            attribute :>> unit = "user::space::AddressSpace::shared_code_at";
        }
        requirement <'L.user.78'> aSharedWordIsOneFutexAcrossFork : ItemLowLevel {
            attribute :>> statement = "shared_object_at shall name, for an address in a
                shared region, the object and byte offset every space mapping that
                object names it by.";
            attribute :>> criterion = "A parent waiting without FUTEX_PRIVATE_FLAG on a
                MAP_SHARED word is not woken by its fork child's private-keyed wake
                of the same word and is woken by the child's shared wake. And with kernel objects alone, on every profile, the `core mem` line (user/rehome_check.rs::check_shared_object_at).";
            attribute :>> parent = "H.MEM.16";
            attribute :>> unit = "user::space::AddressSpace::shared_object_at";
        }

        // --- madvise ---

        requirement <'L.user.79'> droppedAnonymousPagesGoBackAtOnce : ItemLowLevel {
            attribute :>> statement = "advise with Discard or Free on private anonymous
                memory shall give the range's frames back at once and leave the
                range mapped, reading zeros, its neighbours untouched; a hint shall
                drop nothing.";
            attribute :>> criterion = "Of 10 written pages, MADV_DONTNEED of pages 1 to
                8 gives back exactly 8 frames, lowers the resident count by 8, pages
                1 to 8 read 0 and pages 0 and 9 their pattern; MADV_FREE the same;
                12 hints over all 10 pages each answer 0 and every page keeps its
                pattern.";
            attribute :>> parent = ("H.MEM.9", "H.MEM.6");
            attribute :>> unit = ("user::space::AddressSpace::advise",
                "user::space::AddressSpace::advise_region",
                "user::space::Advised::take",
                "user::space::AddressSpace::begin_shootdown",
                "user::space::AddressSpace::shoot",
                "user::space::AddressSpace::resident_pages");
        }
        requirement <'L.user.80'> aDroppedPageKeepsItsForkCopy : ItemLowLevel {
            attribute :>> statement = "advise dropping a page a fork left shared shall
                take only this space's reference, so the other space keeps the
                page's contents.";
            attribute :>> criterion = "After a fork, the parent's MADV_DONTNEED of a
                written page leaves the parent reading 0 there and the child reading
                the page's pattern.";
            attribute :>> parent = "H.MEM.8";
            attribute :>> unit = ("user::space::AddressSpace::advise",
                "user::space::AddressSpace::advise_region",
                "user::space::Advised::take");
        }
        requirement <'L.user.81'> adviceOnAFileMappingSparesTheFile : ItemLowLevel {
            attribute :>> statement = "advise shall drop a private file mapping's
                copies and show the file there again, drop only a shared file
                mapping's translations, take no page out of the file, and refuse
                Free and Remove on a file mapping as Linux does.";
            attribute :>> criterion = "Two copied pages of a private memfd mapping,
                dropped, give back exactly 2 frames and show the file's bytes; a
                shared mapping dropped still shows what it wrote, as the file does;
                MADV_FREE is EINVAL on both, MADV_REMOVE EACCES on the private and
                EOPNOTSUPP on the shared; the file's committed count is unchanged.";
            attribute :>> parent = "H.MEM.9";
            attribute :>> unit = ("user::space::AddressSpace::advise",
                "user::space::AddressSpace::advise_region",
                "user::space::Advised::take", "user::space::removable");
        }
        requirement <'L.user.82'> aHoleIsPunchedInSharedMemory : ItemLowLevel {
            attribute :>> statement = "advise with Remove on shared anonymous memory
                shall take the range's pages out of the object, so every space that
                maps it reads zeros there and the frames go back, and Discard there
                shall keep the contents.";
            attribute :>> criterion = "Of 4 written shared pages seen by a fork child,
                MADV_REMOVE of pages 1 and 2 gives back exactly 2 frames, both spaces
                read 0 there and the pattern at pages 0 and 3; MADV_DONTNEED of page
                0 keeps its pattern; MADV_FREE there is EINVAL.";
            attribute :>> parent = ("H.MEM.6", "H.MEM.9");
            attribute :>> unit = ("user::space::AddressSpace::advise",
                "user::space::AddressSpace::advise_region", "user::space::removable");
        }
        requirement <'L.user.83'> adviceOverAHoleAdvisesTheMappedPart : ItemLowLevel {
            attribute :>> statement = "advise shall advise every mapped part of a range
                and then answer Unmapped for a part no region maps, and shall refuse
                Remove on private anonymous memory as Invalid.";
            attribute :>> criterion = "MADV_REMOVE on private anonymous memory is
                EINVAL; madvise of 0 bytes answers 0; over two pages whose second is
                unmapped MADV_DONTNEED is ENOMEM and the first page reads 0 after,
                and MADV_WILLNEED is ENOMEM.";
            attribute :>> parent = "H.MEM.9";
            attribute :>> unit = ("user::space::AddressSpace::advise",
                "user::space::AddressSpace::advise_region", "user::space::removable");
        }
        requirement <'L.user.84'> lockedAndDeviceRegionsRefuseAdvice : ItemLowLevel {
            attribute :>> statement = "advise shall refuse as Invalid any advice that
                drops pages on a device region, and Discard without locked_too, Free
                and Remove on an mlocked region, dropping nothing there.";
            attribute :>> criterion = "MADV_DONTNEED, MADV_FREE and MADV_REMOVE on an
                mlocked region and MADV_DONTNEED on an I/O mapping are each EINVAL,
                4 of 4, with 0 frames given back and the pages' contents kept;
                MADV_DONTNEED_LOCKED on the mlocked region drops it.";
            attribute :>> parent = "H.MEM.9";
            attribute :>> unit = "user::space::AddressSpace::advise_region";
        }
        requirement <'L.user.85'> adviceRefusedForMemoryChangesNothing : ItemLowLevel {
            attribute :>> statement = "advise that has no memory to note what it would
                take shall answer NoMemory before taking the region's pages or
                translations, the parts before it already advised.";
            attribute :>> criterion = "With each allocation of an MADV_DONTNEED over
                three regions failed in turn, each run answers 0 or EAGAIN, the pages
                of the refused region and after it keep their contents, and 0 frames
                are kept.";
            attribute :>> parent = "H.MEM.11";
            attribute :>> unit = ("user::space::Advised::take",
                "user::space::AddressSpace::advise_region");
        }

        // --- protect ---

        requirement <'L.user.86'> protectTakesTheOldTranslationDown : ItemLowLevel {
            attribute :>> statement = "protect shall take the range's translations out
                of the tables, so the next access is judged by the new permissions,
                and keep the pages' contents.";
            attribute :>> criterion = "After mprotect of a written page to read-only
                the page does not translate, a copy into it is refused, and a copy
                out of it reads what was written. And with kernel objects alone, on every profile, the `core mem` line (user/rehome_check.rs::check_protect_takes_translations_out).";
            attribute :>> parent = "H.MEM.1";
            attribute :>> unit = ("user::space::AddressSpace::protect",
                "user::space::AddressSpace::begin_shootdown",
                "user::space::AddressSpace::shoot");
        }
        requirement <'L.user.87'> protectReachesTheCallersProcessor : ItemLowLevel {
            attribute :>> statement = "protect shall invalidate the old translation on
                the processor that made the call, so the program's next write to a
                page it made read-only faults.";
            attribute :>> criterion = "The `mprotect` program, pinned to another
                processor where there is one, writes a page, makes it read-only and
                writes again, and is ended by SIGSEGV (status 139), not exit 1.";
            attribute :>> parent = "H.MEM.17";
            attribute :>> unit = ("user::space::AddressSpace::protect",
                "user::space::AddressSpace::shoot");
        }
        requirement <'L.user.88'> protectReachesAnotherProcessor : ItemLowLevel {
            attribute :>> statement = "protect shall reach every processor that may
                hold the space's translations, so that a thread on another processor
                cannot write through the writable entry it cached before.";
            attribute :>> criterion = "On a machine with two processors or more, a
                child that wrote a shared page and holds still on its processor has
                the page protected read-only from this one: the page no longer
                translates, and the child's next write ends it with SIGSEGV, 11,
                instead of answering (the `rmap` line).";
            attribute :>> parent = "H.MEM.17";
            attribute :>> unit = ("user::space::AddressSpace::protect",
                "user::space::AddressSpace::begin_shootdown",
                "user::space::AddressSpace::shoot");
        }
        requirement <'L.user.89'> anUnwritableFileMappingStaysUnwritable : ItemLowLevel {
            attribute :>> statement = "protect shall refuse with Refused to make
                writable a range reaching a shared file mapping that may not write its
                file, before changing anything.";
            attribute :>> criterion = "mprotect to read-write of a shared read-only
                mapping of a file opened read-only answers EACCES. And with kernel objects alone, on every profile, the `core mem` line (user/rehome_check.rs::check_protect_refuses_an_unwritable_mapping).";
            attribute :>> parent = "H.MEM.1";
            attribute :>> unit = "user::space::AddressSpace::protect";
        }

        // --- Pages a VMO takes away, and a truncation ---

        requirement <'L.user.90'> aPageTakenAwayIsForgottenInEverySpace : ItemLowLevel {
            attribute :>> statement = "forget_runs shall take down every translation
                the space has of the object's named pages and answer the processors
                that may still cache one, so that the object's shootdown reaches them
                before the frame goes back.";
            attribute :>> criterion = "On a machine with two processors or more, with
                a shared page touched by a parent and its fork child on two
                processors, decommitting it leaves it translated in neither space;
                the given-up frame, claimed and poisoned, is not what the child then
                reads (it reads 0) or writes (the poison stays whole), and the page
                comes back in another frame.";
            attribute :>> parent = "H.MEM.17";
            attribute :>> unit = ("user::space::AddressSpace::forget_runs",
                "user::space::AddressSpace::forget_in",
                "user::space::AddressSpace::begin_shootdown");
        }
        requirement <'L.user.91'> aPendingShootdownWidensTheForget : ItemLowLevel {
            attribute :>> statement = "forget_runs shall ask for the whole TLB of the
                space's processors to be flushed, and answer them, whenever a
                shootdown of the space has begun and not returned, even when it found
                no translation to take down.";
            attribute :>> criterion = "A decommit of a page whose translation a
                concurrent unmap has taken out of the tables, but whose shootdown has
                not returned, is answered with the space's processors and a
                whole-TLB flush, and the frame is claimed back only after that
                flush.";
            attribute :>> parent = "H.MEM.17";
            attribute :>> unit = ("user::space::AddressSpace::forget_runs",
                "user::space::AddressSpace::begin_shootdown");
        }
        requirement <'L.user.92'> aTruncationReachesBothKindsOfFileMapping : ItemLowLevel {
            attribute :>> statement = "A page of a file mapping wholly past the file's
                end shall be refused, shared or private, and a
                truncation shall take a private mapping's copies past the cut, so the
                file grown back shows zeros there.";
            attribute :>> criterion = "A file of 2 pages and 100 bytes, mapped 4 pages
                shared and 4 private and cut to 1 page: page 0 still reads, pages 1
                to 3 are refused in each mapping, 3 of 3 and 3 of 3; grown back to 2
                pages, page 1 reads 0 in both. And with kernel objects alone, on every profile, the `core mem` line (user/rehome_check.rs::check_a_cut_file_refuses_past_its_end, user/rehome_check.rs::check_a_file_grown_back_shows_zeros).";
            attribute :>> parent = ("H.MEM.1", "H.MEM.6");
            attribute :>> unit = ("user::space::commit_page",
                "user::space::AddressSpace::fault_private_file",
                "user::space::AddressSpace::forget_runs", "user::space::cut_shadow");
        }

        // --- File mappings ---

        requirement <'L.user.93'> aSharedFileMappingIsTheFile : ItemLowLevel {
            attribute :>> statement = "A shared file mapping shall show the file's own
                pages, so that a write through it is what the file reads back and a
                write to the file is what it shows.";
            attribute :>> criterion = "A shared mapping of a file of 2 pages and 100
                bytes shows those bytes and zeros to the end of the third page; bytes
                written through it are what the file reads back, and bytes written
                to the file are what it shows. And with kernel objects alone, on every profile, the `core mem` line (user/rehome_check.rs::check_a_shared_mapping_is_the_file).";
            attribute :>> parent = "H.MEM.1";
            attribute :>> unit = ("user::space::AddressSpace::map_file",
                "user::space::AddressSpace::add_file", "user::space::file_placement",
                "user::space::AddressSpace::resolve", "user::space::commit_page");
        }
        requirement <'L.user.94'> aPrivateFileMappingKeepsItsWrites : ItemLowLevel {
            attribute :>> statement = "A private file mapping shall show the file until
                it writes a page and then keep that page to itself, so that neither
                its writes nor a read into it reach the file or a shared mapping,
                while the file's writes still show through pages it has not
                copied.";
            attribute :>> criterion = "The private mapping shows the file's first page;
                a write through it and a read() into it each show in it and in
                neither the file nor the shared mapping; a write to the file shows
                through a page it never copied and not through one it did. And with kernel objects alone, on every profile, the `core mem` line (user/rehome_check.rs::check_a_private_mapping_keeps_its_copies).";
            attribute :>> parent = "H.MEM.8";
            attribute :>> unit = ("user::space::AddressSpace::map_file",
                "user::space::AddressSpace::add_file",
                "user::space::AddressSpace::fault_private_file",
                "user::space::AddressSpace::install_page",
                "user::space::AddressSpace::with_page",
                "user::space::writable_in_place");
        }
        requirement <'L.user.95'> aForkKeepsPrivateFileCopiesApart : ItemLowLevel {
            attribute :>> statement = "fork shall give the child the private file
                mapping's copies, and the child's write into one shall reach neither
                the parent nor the file.";
            attribute :>> criterion = "A fork child reads the parent's private copy;
                its write into a page the parent copied before the fork is seen by
                neither the parent nor the file. And with kernel objects alone, on every profile, the `core mem` line (user/rehome_check.rs::check_a_fork_keeps_private_copies_apart).";
            attribute :>> parent = "H.MEM.8";
            attribute :>> unit = ("user::space::AddressSpace::fork",
                "user::space::attach_child",
                "user::space::AddressSpace::fault_private_file",
                "user::space::AddressSpace::copy_shadow_page",
                "user::space::writable_in_place");
        }
        requirement <'L.user.96'> aProgramsWriteToAReadFilePageCopiesIt : ItemLowLevel {
            attribute :>> statement = "A program's write to a private file mapping's
                page it has only read shall copy the page and go through, not fault
                on the file's read-only page forever, and shall not reach the file.";
            attribute :>> criterion = "A program reads a private file page then writes
                it, and answers within 10 s with the file's word before and its
                marker after; forked and the child dropped, its next write answers
                too; the file's first word is unchanged.";
            attribute :>> parent = "H.MEM.8";
            attribute :>> unit = ("user::space::AddressSpace::fault_private_file",
                "user::space::AddressSpace::install_page");
        }
        requirement <'L.user.97'> aLoaderMapsItsFileAsItNeeds : ItemLowLevel {
            attribute :>> statement = "map_file shall place a fixed private mapping
                exactly where asked, showing the file, an executable one not
                writable, and a writable one made read-only by protect keeping what
                was written.";
            attribute :>> criterion = "A fixed read-execute file mapping lands at its
                address, shows the file's first page and refuses a write; a fixed
                read-write one lands next to it, takes a write, and after mprotect to
                read-only keeps it and refuses the next write. And with kernel objects alone, on every profile, the `core mem` line (user/rehome_check.rs::check_the_loader_pattern).";
            attribute :>> parent = ("H.MEM.1", "H.MEM.18");
            attribute :>> unit = ("user::space::AddressSpace::map_file",
                "user::space::file_placement",
                "user::space::AddressSpace::fault_private_file",
                "user::space::AddressSpace::protect");
        }
        requirement <'L.user.98'> procMapsNamesAFileMapping : ItemLowLevel {
            attribute :>> statement = "with_regions shall show each region with its
                permissions, share mode and file, so that /proc/<pid>/maps names a
                shared writable file mapping by its file.";
            attribute :>> criterion = "/proc/<pid>/maps of the check's process has a
                line marked rw-s that ends in the mapped file's path.";
            attribute :>> parent = "H.MEM.1";
            attribute :>> unit = "user::space::AddressSpace::with_regions";
        }

        // --- Memory charged, failures and giving everything back ---

        requirement <'L.user.99'> faultsStopAtTheJobsMemoryLimit : ItemLowLevel {
            attribute :>> statement = "fault shall be refused when the frame or page
                table it needs would pass the running task's job's memory limit,
                without holding back a sibling job, and a space's drop shall give
                every frame and table it was charged for back.";
            attribute :>> criterion = "Faulting a space in page by page as a task of a
                job limited to 48 pages' worth stops short of 48 pages, the refusal
                counted and the job's memory within one page of its limit; a sibling
                faults all 48 in; with both spaces dropped every level's memory and
                kernel memory read 0 (the `quota` line).";
            attribute :>> parent = "H.QUOTA.2";
            attribute :>> unit = ("user::space::AddressSpace::fault",
                "user::space::AddressSpace::resolve", "user::space::commit_page",
                "user::space::AddressSpace::drop");
        }
        requirement <'L.user.100'> aFailedAllocationLeavesNothingBehind : ItemLowLevel {
            attribute :>> statement = "Every address space operation that allocates --
                fork, the maps, fault, remap and unmap -- shall answer a refused
                allocation with OutOfMemory or absorb it, and keep no frame.";
            attribute :>> criterion = "With the n-th allocation failed alone for every
                n until a run in which none was, each run of the fork, move, shared,
                split, cut, object, stacks, code and page scenarios ends in success or out
                of memory, never another refusal, the run with nothing failed
                succeeds, and each scenario's frame window keeps 0 frames (the
                `sweep` line).";
            attribute :>> parent = "H.MEM.11";
            attribute :>> unit = ("user::space::AddressSpace::add_region",
                "user::vmo::record",
                "user::space::AddressSpace::abandon_region", "user::space::unrooted",
                "user::space::inherited", "user::space::attach_child",
                "user::space::map_error", "user::space::remap_object",
                "user::space::AddressSpace::fork",
                "user::space::AddressSpace::map_file",
                "user::space::AddressSpace::add_file",
                "user::space::AddressSpace::map_window",
                "user::space::AddressSpace::map_object",
                "user::space::AddressSpace::map_shared_code",
                "user::space::AddressSpace::add_fresh",
                "user::space::AddressSpace::drop_fresh",
                "user::space::AddressSpace::move_private",
                "user::space::AddressSpace::remap_backing", "user::space::note",
                "user::space::AddressSpace::give_back",
                "user::space::AddressSpace::drop_unnamed", "user::space::Named::of",
                "user::space::drop_objects", "user::space::AddressSpace::drop");
        }
        requirement <'L.user.101'> stageSixKeepsNoFrameAndNoTable : ItemLowLevel {
            attribute :>> statement = "The address space operations stage 6 checks
                shall give back every frame they took and every page table their
                takedowns emptied, none left on a shootdown list dropped
                unreleased.";
            attribute :>> criterion = "After stage 6's object and address space checks
                0 page tables are counted kept (mm::tables_kept), and the held frame
                count is what it was before them, 0 frames leaked (the `objects`
                line).";
            attribute :>> parent = ("H.MEM.9", "H.MEM.7");
            attribute :>> unit = ("user::space::AddressSpace::unmap",
                "user::space::AddressSpace::take_down",
                "user::space::AddressSpace::protect",
                "user::space::AddressSpace::protect_copied_on_write",
                "user::space::AddressSpace::clear_for_remap",
                "user::space::AddressSpace::shoot",
                "user::space::AddressSpace::drop");
        }

        // --- Needing a check ---

        requirement <'L.user.102'> theCeilingBoundsEveryMapping : ItemLowLevel {
            attribute :>> statement = "set_ceiling shall move the top of the window
                every mapping may reach, refusing an end past the user half or below
                a region still mapped and changing nothing then.";
            attribute :>> criterion = "With the ceiling set to 4 GiB less a page, an
                anywhere mapping lands below it and a fixed one reaching past it is
                refused; setting it past the user half, or below a mapped region, is
                refused BadRange and ceiling() reads as before.";
            attribute :>> parent = "H.MEM.1";
            attribute :>> unit = "user::space::AddressSpace::set_ceiling";
        }
        requirement <'L.user.103'> aDiskFilesPageIsReadBeforeItIsMapped : ItemLowLevel {
            attribute :>> statement = "fault shall have a file's object read a page of
                a file on a disk before mapping it, and answer a page the filesystem
                could not read with Unreadable and one it had no memory for with
                OutOfMemory.";
            attribute :>> criterion = "A shared and a private mapping of a file on a
                disk show its bytes, not zeros, on their first touch; a page whose
                read fails ends the program with SIGBUS.";
            attribute :>> parent = "H.MEM.1";
            attribute :>> unit = ("user::space::AddressSpace::fill_file_page",
                "user::space::AddressSpace::fill_file_pages",
                "user::space::AddressSpace::fill_file_page_alone");
        }
        requirement <'L.user.104'> aFaultIsResolvedWithNoPreemptionLockHeld : ItemLowLevel {
            attribute :>> statement = "fault shall stop a debug kernel, naming the
                outermost lock's site, when it is asked to resolve a fault while a
                lock that disables preemption is held.";
            attribute :>> criterion = "In a debug build, a fault asked for while a
                spin lock is held stops the kernel with the assertion's message and
                that lock's file and line.";
            attribute :>> parent = "H.FAIL.1";
            attribute :>> unit = ("user::space::fault_requested",
                "user::space::AddressSpace::fault");
        }
        requirement <'L.user.105'> anUnmapFreesNothingBeforeItsShootdown : ItemLowLevel {
            attribute :>> statement = "unmap shall give back no page of its range, and
                no page table it emptied, before the shootdown covering them has
                returned from every processor in the space's set.";
            attribute :>> criterion = "On a machine with two processors or more, a
                page a program on another processor keeps reading is unmapped from
                this one; its frame, claimed back and poisoned the moment it is
                free, is never what the program reads: 0 poisoned reads, and the
                program faults.";
            attribute :>> parent = ("H.MEM.7", "H.MEM.17");
            attribute :>> unit = ("user::space::AddressSpace::unmap",
                "user::space::AddressSpace::take_down",
                "user::space::AddressSpace::give_back",
                "user::space::AddressSpace::begin_shootdown",
                "user::space::AddressSpace::shoot");
        }
        requirement <'L.user.106'> aCodePageIsReadAndRunAlone : ItemLowLevel {
            attribute :>> statement = "map_code_page shall map a one-page object as a
                single read-and-run shared page, never writable, and refuse an object
                of any other size before changing the space.";
            attribute :>> criterion = "A two-page object is refused with BadRange and
                the space keeps its regions; a one-page object maps as one region
                read, execute and shared and not writable, one page long, and
                unmapping it leaves the space's regions as they were (the sweep's
                page scenario, the `sweep` line).";
            attribute :>> parent = "H.MEM.18";
            attribute :>> unit = "user::space::AddressSpace::map_code_page";
        }
        requirement <'L.user.169'> aSpaceIsLeftOnlyInAnOrderAShootdownSees : ItemLowLevel {
            doc /* docs/PCID.md section 3; the consultant's P2, ledger line 4734. */
            attribute :>> statement = "begin_shootdown shall count a shootdown before
                it reads the space's set, and install shall join the set before it
                reads the count, both sequentially consistent, so that a processor
                that left the set with the space's translations kept under a PCID
                is either interrupted by a shootdown or flushes the PCID before it
                uses the space again.";
            attribute :>> criterion = "The loom model of the two orders
                (src/tests/loom/tests/pcid.rs, `cargo xtask loom`) finds no
                interleaving in which a processor uses a translation after the
                shootdown that took it down has returned; with either order
                reversed, or the slot's comparison left out, it finds one. The
                switch-back check runs both orders on every boot.";
            attribute :>> parent = "H.MEM.17";
            attribute :>> unit = ("user::space::AddressSpace::install",
                "user::space::AddressSpace::begin_shootdown");
        }
        requirement <'L.user.170'> aSpaceSwitchedBackToSeesItsShootdowns : ItemLowLevel {
            attribute :>> statement = "A space installed again on a processor after
                a shootdown of it began while it was installed elsewhere shall be
                translated through its tables as they are, never through a
                translation the shootdown took down.";
            attribute :>> criterion = "A page moved to a new frame while its space
                is not installed is read, after the switch back, as the new
                frame's marker: decisive on PCID hardware (the N150), where a kept
                tag would read the old frame.";
            attribute :>> parent = "H.MEM.17";
            attribute :>> unit = ("user::space::AddressSpace::install",
                "user::space::AddressSpace::uninstall");
        }
        // The parent is the requirement whose quantity the report counts: the
        // frames a space holds, as L.object.189 takes the cache's. No
        // high-level requirement covers /proc's reports as such.
        requirement <'L.user.171'> theResidentSetSplitsByKind : ItemLowLevel {
            attribute :>> statement = "/proc/<pid>/status shall report VmRSS, RssAnon,
                RssFile and RssShmem from each region's committed pages inside its own
                range: private anonymous memory as RssAnon, shared anonymous memory
                and a memory filesystem's file as RssShmem, a page a private file
                mapping has copied once, as RssAnon and not as its file's, and VmRSS
                their sum; /proc/<pid>/stat's rss shall be VmRSS in pages.";
            attribute :>> criterion = "In the procfs check process, VmRSS equals the
                three parts; two stack pages written for the first time add exactly 8
                kB to RssAnon and nothing to the others; one page of a shared
                anonymous mapping written adds exactly 4 kB to RssShmem alone; a page
                of a tmpfs file mapped shared adds 4 kB to RssShmem alone, and mapped
                shared twice 8 kB; a tmpfs file of eight pages
                with pages 0, 1 and 7 written, mapped as pages 0 and 2 to 7, adds 8 kB
                and not the page in the gap; mapped
                private and then written, it moves 4 kB from RssShmem to RssAnon with
                VmRSS unchanged; stat's field 24 times 4 kB is VmRSS.";
            attribute :>> parent = "H.MEM.9";
            attribute :>> unit = ("user::space::AddressSpace::resident",
                "user::rss::Rss::read",
                "user::space::Resident::total",
                "user::space::counting_of");
        }
        // As L.user.171's, the parent is the frames a space holds.
        requirement <'L.user.172'> aDiskFilesMappedPagesAreItsRss : ItemLowLevel {
            attribute :>> statement = "A disk file's pages inside a region's range shall
                count as RssFile, the file's other cached pages not at all, and a page
                a private mapping of it has written as RssAnon instead.";
            attribute :>> criterion = "With an eight-page file on the stage 12 disk all
                in the cache, a read-only mapping of pages 2 to 5 counts exactly 4
                file pages and no others; a private mapping of page 0, written,
                counts 1 anonymous page and no file page. And with kernel objects alone, on every profile, the `core mem` line (user/rehome_check.rs::check_a_disk_file_counts_as_a_file).";
            attribute :>> parent = "H.MEM.9";
            attribute :>> unit = ("user::space::AddressSpace::resident",
                "user::space::counting_of",
                "user::vmo::Vmo::is_disk_file");
        }
        // docs/RSS-COUNTS.md: the counts L.user.171 reports, kept where the
        // regions and the pages meet instead of counted for every reader. The
        // parent is the frames a space holds, as L.user.171's.
        requirement <'L.user.236'> theKeptCountsAreTheRecount : ItemLowLevel {
            attribute :>> statement = "A space's kept RssAnon, RssFile and RssShmem
                shall each equal L.user.171's count whenever no operation changing
                its regions or the pages of an object it maps is in progress.";
            attribute :>> criterion = "With kernel objects alone, on every profile
                (the `core rss` line), the kept counts equal a recount after a first
                touch of eight pages, an mprotect split and merge, an unmap of a
                middle, madvise(DONTNEED), a shared mapping touched, a fork in both
                spaces, write faults in the child and the parent, the child's drop,
                and about 4,000 regions over one reserve: 12 comparisons, all
                equal. In the
                rss check process (stage 8), the kept
                counts equal a recount of every region's object after each of: a
                new mapping; a first touch of eight pages; an mprotect split and
                its merge; an munmap of a region's middle; madvise(DONTNEED); an
                munmap of whole regions; a fork, in parent and child; a
                copy-on-write write in the child and in the parent; a child's write
                to shared anonymous memory, in both; the child's exit, after which
                an object it alone mapped counts for nobody; a memfd mapped shared
                twice and private once; the private mapping's write; a fork with
                the private mapping's copies and a write to them in the child; a
                truncation under the copies and the file grown back; an mremap
                moving a private region over a fixed destination; shared anonymous
                memory touched, grown by mremap, moved over a fixed destination and
                shrunk (its placement is counted in while the old range still
                covers the same pages, one id's index ranges overlapping for that
                moment); 4,000 regions in Wine's pattern with a fixed mapping into
                the reserve; a file of 4,096 cached pages mapped, and written beside
                64 mappings; a private file mapping writing and dropping each of
                1,024 pages, whose file view's mask then holds an entry for each,
                every one charged; 34 comparisons, all equal. With the stage 12 disk, a
                disk file mapped shared and private with one page copied, a reclaim
                that took some of its clean pages, and the pages faulted back in:
                equal after each. Not
                reached by a check, and argued: a refused mremap move (the fresh
                object's adopted pages leave it by disown_pages through the same
                funnel before it is dropped), a pager's supply (put_supplied and
                take_for_supply change pages only through the funnel).";
            attribute :>> parent = "H.MEM.9";
            attribute :>> unit = ("user::rss::Rss::slot",
                "user::rss::Rss::add",
                "user::rss::Rss::take",
                "user::rss::Rss::shift",
                "user::rss::ViewKey::names",
                "user::rss::View::weight",
                "user::rss::ShadowLink::mask",
                "user::rss::ShadowLink::unmask",
                "user::rss::Frames::counted",
                "user::rss::Frames::insert_held",
                "user::rss::Frames::try_insert",
                "user::rss::Frames::replace",
                "user::rss::Frames::remove",
                "user::rss::Frames::take_all",
                "user::rss::Frames::dropping",
                "user::rss::Frames::mask_index",
                "user::rss::Frames::unmask_index",
                "user::rss::Frames::view_masking",
                "user::rss::Mask::clear",
                "user::rss::Frames::masked_view",
                "user::rss::Frames::link_to",
                "user::rss::Frames::reserve_lowers",
                "user::rss::Frames::cover_step",
                "user::rss::Frames::view_for",
                "user::rss::View::room",
                "user::rss::View::change",
                "user::rss::unmasked_chunk",
                "user::rss::Mask::new",
                "user::rss::Mask::masked",
                "user::rss::Mask::set",
                "user::rss::Frames::forget",
                "user::vmo::Vmo::with_frames_nested",
                "user::vmo::Vmo::with_frames",
                "user::vmo::Vmo::cover",
                "user::vmo::Vmo::reserve_lowers",
                "user::vmo::Vmo::link_shadow",
                "user::vmo::Vmo::forget_views",
                "user::vmo::PagesLock::take",
                "user::vmo::PagesGuard::drop",
                "user::space::counting",
                "user::space::counted_later",
                "user::space::Counting::raise",
                "user::space::Counting::lower",
                "user::space::Counting::reserve_lower",
                "user::space::AddressSpace::count_in",
                "user::space::AddressSpace::count_out",
                "user::space::AddressSpace::count_out_removed",
                "user::space::AddressSpace::room_to_count_out",
                "user::space::Counting::view_order",
                "user::space::AddressSpace::count_remap_in",
                "user::space::AddressSpace::undo_move",
                "user::space::AddressSpace::count_out_unplaced",
                "user::space::AddressSpace::clear_ranges",
                "user::space::placed_backing");
        }
        // docs/RSS-COUNTS.md §5: what a read of them costs. The parent is
        // L.user.171's, as no high-level requirement states a report's cost.
        requirement <'L.user.237'> aReadOfTheCountsIsConstant : ItemLowLevel {
            attribute :>> statement = "Reading a space's resident counts shall take no
                lock and do work independent of the number of its regions and of
                its objects' pages.";
            attribute :>> criterion = "By analysis: AddressSpace::resident is three
                relaxed loads of the space's Rss (Rss::read), and procfs's status
                and stat call it and nothing else for their resident figures. By
                test, in the rss check process: 200 reads over a space of about
                4,000 regions take no more than four times 200 over a space of one
                region and a millisecond; a recount takes milliseconds a read at
                that size; the same bound over about 4,000 regions made with kernel
                objects alone, on every profile (the `core rss` line).";
            attribute :>> parent = "H.MEM.9";
            attribute :>> unit = ("user::space::AddressSpace::resident",
                "user::rss::Rss::read");
        }
        // docs/RSS-COUNTS.md §8: status's other figures, which walked every
        // region too. The parent is L.user.171's, for the same reason.
        requirement <'L.user.238'> theRegionFiguresAreKept : ItemLowLevel {
            attribute :>> statement = "/proc/<pid>/status's VmSize, VmLck and VmData
                and /proc/<pid>/stat's vsize shall be the region map's totals, kept
                as regions are mapped, unmapped and protected, of every region, the
                mlocked ones, and the private writable ones less the one holding the
                start stack pointer; VmStk shall be that one region, found by one
                lookup.";
            attribute :>> criterion = "In the procfs check process, the figures from
                the kept totals equal a walk of every region (Memory::walked) for
                the process as it is, after a private and a shared mapping, an
                mprotect splitting the private one, an unmap of the shared one's
                middle, an unmap of its rest, and with every mapping of the check
                gone. With kernel objects alone, on every profile (the `core rss`
                line), the totals equal a sum over the regions after each of the
                changes that line makes. The map's host tests hold the kept totals equal to a sum over
                the regions after every insert, removal, MAP_FIXED, protect and
                fork they make (check_invariants).";
            attribute :>> parent = "H.MEM.9";
            attribute :>> unit = "user::space::AddressSpace::region_totals";
        }
        // docs/RSS-COUNTS.md §9: /proc/meminfo's page-cache figures kept as
        // pages come and go (consultant ledger 8919 M1). The parent is
        // L.object.189's, whose figures these are.
        requirement <'L.user.239'> theCacheFiguresAreKeptShares : ItemLowLevel {
            attribute :>> statement = "totals shall answer each of L.object.189's
                figures as the sum over every live cache object of what it gives:
                its pages; its dirty count, its filesystem's count as last read and
                its page states, at most its pages; and for a reclaimable object its
                pages less that dirty count. The sum shall be kept as the object's
                pages lock is let go and as its filesystem tells of a change, shall
                never be below zero, and shall equal those per-object figures
                whenever no change is under way.";
            attribute :>> criterion = "With kernel objects alone, on every profile
                (the `core pc-kept` line): over a memory filesystem's object, a
                reclaimable disk file's, one reclaim may not take and one dirty
                before its object was made, after pages committed, a source's dirty
                count moved and told, page states set Dirty, awaiting clean and
                Clean, the cap reached and pages decommitted, every object's share
                equals the walk's figures for it and the machine's sum equals the
                walk (user::cache_kept_check::walked_totals) on a reading two
                agreeing walks bracket, and after the objects are dropped. On the
                stage 12 writable mount (the `pc-kept` line), the same after a
                write, a sync in slices, a page written again, a shared mapping's
                write, a truncation and the sync after it. The btrfs host test
                every_change_of_a_dirty_set_tells_its_store_the_count_after_it holds
                every change of a dirty set, the failed returns of a writeback
                included, to a telling of the count after it.";
            attribute :>> parent = "H.QUOTA.12";
            attribute :>> unit = ("user::cache::Share::settle",
                "user::cache::Share::give", "user::cache::Share::take_back",
                "user::cache::Share::read_fs", "user::vmo::Vmo::dirty_changed",
                "user::vmo::PagesGuard::drop", "user::vmo::Vmo::drop",
                "user::vmo::Vmo::new_filled");
        }
        // docs/RSS-COUNTS.md §9.4: what a read of them costs.
        requirement <'L.user.240'> aReadOfTheCacheFiguresTouchesNoObject : ItemLowLevel {
            attribute :>> statement = "A read of the page cache's kept figures shall
                take only the early counts and each processor's record, touching no
                cache object, list or lock.";
            attribute :>> criterion = "By analysis: totals is totals_except(None),
                four relaxed loads from the early counts and from each record of the
                topology's processors. By test, with kernel objects alone on every
                profile (the `core pc-kept` line): a check-build count of the lists
                of live objects made is unchanged across 200 reads of totals with
                4,096 cache objects more live; the time of those reads is reported
                beside 200 with few.";
            attribute :>> parent = "H.QUOTA.12";
            attribute :>> unit = ("user::cache::totals", "user::cache::totals_except");
        }
        // docs/RSS-COUNTS.md §9.4, K10 of ledger 8701: no line every
        // processor writes.
        requirement <'L.user.241'> aSettleAddsToItsOwnProcessor : ItemLowLevel {
            attribute :>> statement = "A settle of a cache object's share shall add
                to the record of the processor it runs on, or to the early counts
                before that record can be found.";
            attribute :>> criterion = "With kernel objects alone, on every profile
                with two processors or more (the `core pc-kept` line, run with
                --smp 2 on ARMv7-A): a task on processor 1, preemption held off,
                commits 8 pages to a check disk object, and processor 1's record's
                disk count moves by exactly 8.";
            attribute :>> parent = "H.QUOTA.12";
            attribute :>> unit = "user::cache::here";
        }
        // docs/ANON-MERGE.md §5.1 (consultant ledger 9131, 9155, 9183): the
        // term the two below use, defined first. ferrix_vma's split and merge
        // keep the line too (try_merge_at, contiguous_backing,
        // Backing::advanced_by); they are a library no ring classifies yet
        // (F-76), so the analysis names them and the units below do not.
        requirement <'L.user.244'> ownAnonymousObjectsAreOnOneLine : ItemLowLevel {
            attribute :>> statement = "For each own private anonymous object X of a
                space (one no handle, file or shadow of the space names, named only
                by private anonymous regions) there shall be a base b(X) such that
                every region of the space naming X names offset v - b(X) at each of
                its addresses v; so no two addresses of the space name one page of
                X.";
            attribute :>> criterion = "By analysis (docs/ANON-MERGE.md §5.1, each
                path named: map_anonymous and map_anywhere at offset 0, the reuse on
                its neighbour's line, splits by Backing::advanced_by, ferrix_vma's
                merge keeping the left offset, abandon_region and the remap undo
                paths removing a region whole, a private mremap moving into a new
                object, fork copying by id). With kernel objects alone, on every
                profile (the `core anm` line), every own private anonymous object of
                each case's space, after every step, is named only by private
                anonymous regions and on one line
                (user::space::own_lines_for_check); a negative control letting a
                shared mapping join a private object fails it.";
            attribute :>> parent = "H.MEM.1";
            attribute :>> unit = ("user::space::AddressSpace::map_fresh",
                "user::space::AddressSpace::place_beside",
                "user::space::beside_of",
                "user::space::moved_object",
                "user::space::carry_apart");
        }
        // docs/ANON-MERGE.md §5.3 (consultant ledger 9131 A5, 9155, 9183
        // A15): which neighbour, and every reason to decline.
        requirement <'L.user.242'> anonymousMappingsJoinTheirNeighbour : ItemLowLevel {
            attribute :>> statement = "A private anonymous mapping made by mmap
                (MAP_FIXED or not) or brk shall be made in the object of its left
                neighbour if that neighbour qualifies, else of its right neighbour
                if that one qualifies, else in a new object. A neighbour qualifies
                when its object is own private anonymous (L.user.244), the region
                and the new mapping are private, the new range is free (no region
                of the space reaches into it), the offset is not negative, the
                space is not marked as being emptied and is not a window or region
                space, the object is plain (not sealed, pager-backed, coherent or
                combining, no kernel view, one mapper) and the region is not the
                exec stack's or a guard of it. The mapping is made at the left
                neighbour's offset plus its length, or the right's offset less the
                new length, when the object holds no held page there; otherwise in
                a new object, with no try of the other side.";
            attribute :>> criterion = "With kernel objects alone, on every profile
                (the `core anm` line): Wine's pattern of views mapped, decommitted
                and released MAP_FIXED into one reserve, each taking the reserve's
                object, and one region once an mprotect makes the protections
                equal (ferrix_vma's merge joining what has equal flags); brk's
                steps one region and one object; a right neighbour with room
                taken; declined, each with a new object: a right neighbour at
                offset 0, a shared neighbour, a shared mapping beside a private
                one, an object mapped by handle, private memory allocated by
                handle, a region kept apart as exec keeps
                its stack and guards, a space being emptied, a window holding a
                held page; a heap step asked over a mapped, written page (brk's way,
                no unmap first) refused, taking nothing; 4,000 views in one reserve
                on one object unmapped whole. Negative controls: the reuse off, the
                right neighbour's room check, the handle test, the emptier's mark,
                the kept-apart mark and the free-range test each left out.";
            attribute :>> parent = ("H.MEM.1", "H.MEM.9");
            attribute :>> unit = ("user::space::Layout::map_anonymous_beside",
                "user::space::Layout::map_anywhere_beside",
                "user::space::AddressSpace::place_beside",
                "user::space::range_free",
                "user::space::own_line",
                "user::space::AddressSpace::keep_apart",
                "user::space::AddressSpace::mark_emptying",
                "user::vmo::Vmo::join_window");
        }
        // docs/ANON-MERGE.md §5.4 (consultant ledger 9155 A9 (i), A11, 9183
        // A16): a reused window reads as a new object's would.
        requirement <'L.user.243'> anonymousMappingsReadZero : ItemLowLevel {
            attribute :>> statement = "Each page of a private anonymous mapping
                shall read as zero until written, whether it was made in a
                neighbour's object or a new one.";
            attribute :>> criterion = "With kernel objects alone, on every profile
                (the `core anm` line), every page of the mapping read: a window
                whose written page an unmap kept for a second reference, mapped
                again in the same object (its page taken back); a window whose
                written page is held, declined and mapped in a new object; a window
                written, unmapped and mapped again; a region moved out by mremap
                and its window mapped again; Wine's released views holding no page;
                a heap step asked over a mapped, written page (brk's way, no unmap
                first) refused, the page keeping its frame and byte. Negative
                controls: the held-page check, the take-back and the free-range
                test each left out, each on its window with a non-zero page.";
            attribute :>> parent = "H.MEM.1";
            attribute :>> unit = ("user::vmo::Vmo::join_window",
                "user::space::AddressSpace::retire_window");
        }
        // F-112 (consultant ledger 9098, 9112 E6): the sorts on the unmap
        // path, whose length is a program's number of regions.
        requirement <'L.user.245'> anUnmapSortsWithoutRecursion : ItemLowLevel {
            // Restated by D2 (docs/EXIT-TEARDOWN.md 4.2, ledger 9543 ET.4 f,
            // 9611 X8): an exit no longer unmaps (L.user.247), so the sort is
            // reached by munmap, mremap, a fixed map over a mapping and the OOM
            // emptier's chunks.
            attribute :>> statement = "An unmap shall order the regions it
                removes, and the ids and views they name, without recursion, in a
                stack of the same size at any number of regions.";
            attribute :>> criterion = "check-stack-depth, on all three
                architectures: every recursion a judged line reaches -- the way
                out of a system call, which reaches munmap's unmap, and the OOM
                emptier, whose chunks are unmaps -- is listed in RECURSIONS with
                its bound, and none is in give_back, room_to_count_out or
                Named::of; control: core's recursive sort put back in give_back
                (ids.sort_unstable) -- the row's 'recursion on a judged path, not
                listed' line naming core's median3_rec (sr6-sort-stack, and again
                on D2's tip). The depth itself did not decide it: on four-page
                stacks core's sort stopped the kernel with FX-9004 at 60,000
                regions, but on five pages a paint of the stack (x86-64 release,
                KVM, 60,020 ids) read it within 1,800 bytes of the guard, not
                over it, against at most 512 bytes for sort_flat_by_key.
                ferrix-fallible's host
                tests hold sort_flat_by_key's result in order and a permutation of
                its input at lengths 0 to 60,000, ascending, descending, equal and
                random, for a pair and a tuple key.";
            attribute :>> parent = "H.MEM.9";
            // The sort itself is ferrix-fallible's (sort_flat_by_key, sift_down,
            // larger), a crate the manifest does not list as a member (F-56),
            // so its functions cannot be units here; its host tests are in
            // the criterion.
            attribute :>> unit = ("user::space::all_still_named",
                "user::space::AddressSpace::give_back",
                "user::space::AddressSpace::room_to_count_out",
                "user::space::Named::of");
        }
        // docs/EXIT-TEARDOWN.md 4.2, D2 (ledger 9543 ET.5, 9611; F-114).
        requirement <'L.user.247'> anEndIsNeverRefused : ItemLowLevel {
            attribute :>> statement = "A process's end shall leave no region,
                translation or page table in its user half, and release every
                object only it maps, before its waiter is told; no refused
                allocation shall stop or postpone it.";
            attribute :>> criterion = "Boot check (stage 6, user::check's
                check_a_space_emptied_at_its_end_with_every_allocation_refused): a
                fork child of 16 one-page regions of its own and 4 pages shared
                with its parent is emptied with every fallible allocation of the
                task refused; its map is empty and its resident pages 0, its
                parent's unchanged, the injection clear after, inside the stage's
                frame window. Control: the emptying replaced by the general unmap --
                'a space's end left regions or resident pages when its allocations
                were refused' (FX panic; ex6-c-core). The memory sweep's 'end'
                scenario (user::alloc_check): each allocation of a space's end,
                with an object another space maps, failed in turn, leaves no region
                and no resident page, the other space's page kept, nothing kept.
                Boot check (stage 7, the syscall layer's
                check_an_end_is_never_refused): a fork child of 256 one-page
                regions of its own and 16 shared with its parent is ended with
                every fallible allocation of the ending task refused
                (fallible::inject); its map is empty, its counts and its map's
                totals 0, at least 256 frames less a slack of 16 are back, its
                parent's resident pages are unchanged, and the injection is clear
                after. Control: the release put back on the general unmap --
                'left regions or resident pages when its allocations were
                refused' (FX panic). test-exit-regions' enomem phase on x86-64
                KVM, AArch64 and ARMv7-A at --smp 2, release: a child that mapped
                until mmap refused it exits, and MemFree while it is a zombie
                (waitid with WNOWAIT) and at waitpid's return is within the
                larger of 16 MiB and 2% of MemFree before, its zombie VmRSS 0, a
                figure it cannot read failing the phase; control: on AArch64, the
                release put back on the general unmap for a space of more than
                4,096 regions only (so that the stage-7 case above still passes) --
                'memory was not back'. ferrix-vma's host test
                take_moves_every_region_out_and_leaves_nothing_counted.";
            attribute :>> parent = "H.MEM.9";
            // ferrix-vma's take is a crate the manifest does not list as a
            // member (F-76); its host test is in the criterion.
            attribute :>> unit = ("user::space::AddressSpace::empty_for_exit",
                "mm::prune_in_unlinking",
                "user::rss::Rss::clear");
        }
        // docs/RAM-RELEASE.md §3: the clean btrfs nodes, reclaimable heap.
        requirement <'L.user.175'> cleanBtrfsNodesAreAvailable : ItemLowLevel {
            attribute :>> statement = "/proc/meminfo's SReclaimable shall be the bytes the
                writable btrfs mounts' clean tree nodes hold, and MemAvailable shall
                count them besides the free frames and the clean page cache.";
            attribute :>> criterion = "With a wide directory read on the stage 12 disk,
                SReclaimable is the mounts' count in KiB, and MemAvailable exceeds
                the free frames and reclaimable pages by that count within half the
                volume's clean bytes (the `reclaim` line of test-btrfs).";
            attribute :>> parent = "H.QUOTA.12";
            attribute :>> unit = "ferrix_btrfs_write::volume::WriteVolume::clean_bytes";
        }
        // docs/RAM-RELEASE.md §2, R1 (consultant ledger 4971, 5022, 5038).
        requirement <'L.user.174'> devmgrStartsAgainFromTheKeptSet : ItemLowLevel {
            attribute :>> statement = "Under ferrix.devmgr=init every devmgr start
                after the first shall be made from the program, names and driver
                images the first start read, kept by the kernel, never from a path,
                and shall be refused when their fingerprint is not the one taken
                when they were kept.";
            attribute :>> criterion = "After the release, svc restart
                devmgr.service starts a second devmgr whose line says it came from
                the kept set, and / written, synced and read back afterwards answers
                what was written; a kept set whose stored fingerprint differs is
                refused with the line saying it is not as it was kept, and no
                second devmgr starts (test-init and its control).";
            attribute :>> parent = "H.DEV.4";
            attribute :>> unit = ("discovery::devmgr::read_files",
                "discovery::devmgr::read_set", "discovery::devmgr::fingerprint");
        }
    }

    package AddressWaits {
        doc /* K5 of docs/MICROKERNEL.md section 3, docs/microkernel/K5.md:
             * the core's one table of waits on a user address, which the
             * native calls address_wait and its family and the load ring's
             * futex both answer from. The consultant's OK IF (1)-(8), ledger
             * line 2498. Checks: user::address_wait_check, stage 9's
             * `addrwait` line; the load ring's futex checks stay as the
             * regression gate for Linux. */

        requirement <'L.user.135'> aWordIsKeyedByItsSpaceOrItsObject : ItemLowLevel {
            attribute :>> statement = "Key::new shall key a word by its address space
                and user address, unless shared is asked for and a shared region
                holds the word, when it shall key it by the region's VMO and the
                word's byte offset in it; Key::in_object shall key a word named by a
                VMO and an offset by the same VMO and offset; and the bucket a key
                is listed in shall be a hash of it under a key seed sets from the
                boot's random bytes.";
            attribute :>> criterion = "A wait through a shared mapping in one process
                is found by a shared wake through another process's mapping at
                another address, and by a wake by handle from a process with no
                mapping, and not by a private wake (the `addrwait` line; controls C2
                and C3, the shared key by address and the handle's key on another
                offset, fail it).";
            attribute :>> parent = "H.OBJ.20";
            attribute :>> unit = ("user::address_wait::Key::new",
                "user::address_wait::Key::in_object", "user::address_wait::Key::bucket",
                "user::address_wait::Key::eq", "user::address_wait::fold",
                "user::address_wait::seed");
        }
        requirement <'L.user.136'> noWakeIsLost : ItemLowLevel {
            attribute :>> statement = "list shall read a wait's word and put the
                waiter on the table under one hold of the lock of the key's bucket,
                listing nothing when the word does not hold the value given; a wake
                shall look under the same lock.";
            attribute :>> criterion = "A wait on a changed word answers SHOULD_WAIT and
                leaves nothing listed; a listed waiter is woken by one wake of its
                word and answers 0 (the `addrwait` line; controls C1 and C4 fail
                it).";
            attribute :>> parent = "H.OBJ.20";
            attribute :>> unit = ("user::address_wait::list",
                "user::address_wait::wait_on");
        }
        requirement <'L.user.137'> theReadUnderTheLockNeverFaults : ItemLowLevel {
            attribute :>> statement = "The read of a word under a bucket's lock shall
                neither fault, fill nor commit a page: a page not there shall make
                the caller let go of the lock, read the word with nothing held, and
                read again; a page of a VMO never committed that has nothing to fill
                it from shall read as zero and stay uncommitted.";
            attribute :>> criterion = "A wait by handle on a word in a VMO page never
                committed reads zero and leaves the VMO's committed pages as they
                were; a wait on a word whose page is there makes no read with
                nothing held, and a wait on a word whose page was never touched
                reads it with nothing held, lists on a later round and is woken
                (the `addrwait` line, case 15; a list that refuses a page not there
                fails it).";
            attribute :>> parent = "H.OBJ.20";
            attribute :>> unit = ("user::address_wait::read_word",
                "user::address_wait::read_present_word", "user::address_wait::list");
        }
        requirement <'L.user.138'> aWakeTakesTheOldestByItsBitset : ItemLowLevel {
            attribute :>> statement = "wake shall rouse at most its limit of waiters
                on its key whose bitset shares a bit with its own, oldest first, none
                for a limit of zero, take a stale entry of a waiter already woken off
                without counting it, take entries off in rounds of at most 32 per
                hold of the lock, and drop them after it.";
            attribute :>> criterion = "Of three waiters, a wake of zero rouses none, a
                wake of two the two oldest, a wake whose bitset shares no bit with
                the third none and one that shares a bit the third; a wake over 1,024
                dormant entries of one bucket rouses none and is timed (the
                `addrwait` line).";
            attribute :>> parent = "H.OBJ.20";
            attribute :>> unit = ("user::address_wait::wake",
                "user::address_wait::rouse", "user::address_wait::Sleeper::rouse");
        }
        requirement <'L.user.139'> aRequeueMovesAcrossBuckets : ItemLowLevel {
            attribute :>> statement = "requeue shall take both buckets' locks, the
                lower-numbered first; with a compared word, read it under both locks
                and move nothing if it holds another value; make the room every
                entry that may move needs before taking any off, letting go of both
                locks to allocate it; and move each entry onto the target's bucket,
                recording the bucket in its waiter.";
            attribute :>> criterion = "Two waiters on a word are moved by a requeue
                to a word in another bucket and woken there by a wake of two; a
                compared requeue of a changed word answers SHOULD_WAIT and moves
                none (the `addrwait` line; control C5 fails it).";
            attribute :>> parent = "H.OBJ.20";
            attribute :>> unit = ("user::address_wait::requeue",
                "user::address_wait::take_and_move", "user::address_wait::still_holds",
                "user::address_wait::room_needed", "user::address_wait::make_room");
        }
        requirement <'L.user.140'> aWaitOnManyWordsAnswersWhich : ItemLowLevel {
            attribute :>> statement = "wait_on shall list one entry per word, answer
                the index of the word whose wake took the waiter, and take every
                entry off the table before it returns, however it ends.";
            attribute :>> criterion = "A wait on three words woken through the second
                answers 1 and leaves no entry on any of the three (the `addrwait`
                line).";
            attribute :>> parent = "H.OBJ.20";
            attribute :>> unit = ("user::address_wait::wait_on",
                "user::address_wait::leave", "user::address_wait::list_every");
        }
        requirement <'L.user.141'> aDeadlineEndsAWaitNeverEarly : ItemLowLevel {
            attribute :>> statement = "wait_on shall end a wait with TimedOut once its
                absolute CLOCK_MONOTONIC deadline has passed and not before, sleeping
                on the scheduler's own deadline and no timer of its own; a waiter
                woken answers woken even when its deadline has also passed.";
            attribute :>> criterion = "A wait whose deadline has passed answers
                TIMED_OUT at once; a wait whose deadline is 5 ms on answers TIMED_OUT
                no sooner than that deadline, on the clock that set it (the
                `addrwait` line; control C7 fails it).";
            attribute :>> parent = "H.OBJ.20";
            attribute :>> unit = ("user::address_wait::wait_on",
                "user::address_wait::sleep");
        }
        requirement <'L.user.142'> anEndingCallerLeaves : ItemLowLevel {
            attribute :>> statement = "wait_on shall end a wait with Interrupted once
                the caller's personality says it must leave, and leave nothing of it
                on the table.";
            attribute :>> criterion = "A waiter whose process is killed answers EINTR
                and is not listed (the `addrwait` line).";
            attribute :>> parent = "H.OBJ.20";
            attribute :>> unit = "user::address_wait::wait_on";
        }
        requirement <'L.user.143'> aWaitOutlivesItsMapping : ItemLowLevel {
            attribute :>> statement = "A listed wait shall stay listed when the
                mapping of its word is unmapped, its shared key holding its VMO; a
                wait on an address no region maps shall answer Fault and list
                nothing.";
            attribute :>> criterion = "A waiter by mapping whose mapping is unmapped
                stays listed and is woken by a wake by handle; a wait on the
                unmapped address answers FAULT (the `addrwait` line).";
            attribute :>> parent = "H.OBJ.20";
            attribute :>> unit = ("user::address_wait::Key::new",
                "user::address_wait::read_word");
        }
        requirement <'L.user.144'> aWaiterIsChargedAndBucketsShrink : ItemLowLevel {
            attribute :>> statement = "wait_on shall charge a waiter, its bucket
                records and one entry's room per word to the payer's job before
                anything is listed, refusing with NoMemory and listing nothing when
                the job's limit refuses it, and give the charge back when the waiter
                is dropped; a bucket shall grow and shrink only by a vector
                allocated and freed with no bucket's lock held, and keep at most four
                times its entries' room above MIN_ROOM.";
            attribute :>> criterion = "A wait in a job with no memory to spare
                answers NO_MEMORY while a sibling job's goes on; a sleeping waiter is
                charged to its job and the charge is gone once it returns; a bucket
                of 1,024 dormant entries gives its room back once they leave (the
                `addrwait` line; control C6 fails it).";
            attribute :>> parent = ("H.OBJ.20", "H.QUOTA.2");
            attribute :>> unit = ("user::address_wait::new_sleeper",
                "user::address_wait::cost", "user::address_wait::grow",
                "user::address_wait::shrink", "user::address_wait::move_into",
                "user::address_wait::shrink_due", "user::address_wait::shrink_if",
                "user::address_wait::source_shrink_due");
        }
        // docs/BLOCK-AND-WAKE.md W1: a futex wait blocks on no queue, so the
        // order of the wake and the block is the fence pair's (ledger 9027, WF6).
        requirement <'L.user.246'> aWakeFindsTheWaiterBlockedOrItsMark : ItemLowLevel {
            attribute :>> statement = "A wake that marks a waiter woken and the
                waiter's block shall be ordered so that the wake finds the waiter
                blocked or the waiter's last look finds the mark.";
            attribute :>> criterion = "Two racers on two processors hand a turn
                back and forth 1,000 times through two words, each wait bounded at
                200 ms, well under the 1 s recheck; no wait times out with its word
                at the round and the other racer's wake for it made (the `addrwait`
                line, case 14; a rouse that marks and does not wake fails it).";
            attribute :>> parent = "H.OBJ.20";
            attribute :>> unit = ("user::address_wait::Sleeper::rouse",
                "user::address_wait::sleep", "sched::wait::WaitQueue::wait_on_any");
        }
    }

    package SpacesByHandle {
        doc /* K2 of docs/MICROKERNEL.md section 3 (docs/microkernel/K2.md,
             * slice A; the consultant's OK IF, ledger 2845 and 2857): what the
             * address space keeps of a mapping made by handle. Stage 9's `space`
             * line verifies each. */

        requirement <'L.user.200'> theFirstImageIsLoadedAsItAsks : ItemLowLevel {
            attribute :>> statement = "first_image::load shall map every PT_LOAD of an image into an empty space as anonymous memory, the file bytes copied, .bss zero, permissions by page.";
            attribute :>> criterion = "A two-segment image's bytes read back; an executable leaf and no W+X leaf in the sweep (the `build` line).";
            attribute :>> parent = "H.MEM.27";
            attribute :>> unit = ("discovery::first_image::load");
        }

        requirement <'L.user.201'> theFirstImageHasNoWXPage : ItemLowLevel {
            attribute :>> statement = "first_image::load shall refuse an image with a page that would be writable and executable, with nothing mapped.";
            attribute :>> criterion = "An RWX segment and two segments sharing a page: WriteExecute, no region left (the `build` line).";
            attribute :>> parent = "H.MEM.27";
            attribute :>> unit = ("discovery::first_image::load", "discovery::first_image::flags_of");
        }

        requirement <'L.user.202'> theFirstImageRefusesWhatCannotRun : ItemLowLevel {
            attribute :>> statement = "first_image::load shall refuse another machine or class, a PT_INTERP, an entry or a segment outside user space, a truncated header and no loadable segment, without a stop.";
            attribute :>> criterion = "Seven malformed images, each refused (the `build` line).";
            attribute :>> parent = "H.MEM.27";
            attribute :>> unit = ("discovery::first_image::load", "discovery::first_image::moved");
        }

        requirement <'L.user.203'> theFirstStackIsPlaced : ItemLowLevel {
            attribute :>> statement = "first_image::load shall place the stack and its guards where ferrix-native-abi's constants say, as the loader library does.";
            attribute :>> criterion = "The three regions read back at their addresses and permissions (the `build` line); a compile-time assertion against exec.rs's constants.";
            attribute :>> parent = "H.MEM.27";
            attribute :>> unit = ("discovery::first_image::place_stack");
        }

        requirement <'L.user.204'> theElfParserValidates : ItemLowLevel {
            attribute :>> statement = "ferrix-elf's parse, validate_segments_within and load_span shall refuse a header or segment outside the image.";
            attribute :>> criterion = "ferrix-elf's host tests and the elf_parse fuzz target, gate-level rows.";
            attribute :>> parent = "H.MEM.27";
            attribute :>> unit = ("discovery::first_image::elf_bytes");
        }

        requirement <'L.user.205'> firstImageHasOneCaller : ItemLowLevel {
            attribute :>> statement = "first_image::load shall be called only from discovery/devmgr.rs and check files, and no other product file but the Linux loader's shall parse an ELF.";
            attribute :>> criterion = "check-item-boundary.py's loader rule, with a planted caller failing it.";
            attribute :>> parent = "H.MEM.26";
            attribute :>> unit = ("discovery::first_image::load");
        }

        requirement <'L.user.206'> aMappedWriteIsSeen : ItemLowLevel {
            attribute :>> statement = "A Clean page of a sourced object shall be installed read-only by every mapping, and its first write through a mapping, a fork child's included, shall mark it Dirty.";
            attribute :>> criterion = "Through the fault a store takes: leaf read-only, state Clean, then Dirty and writable; a program's own store from ring 3 marks its page and no other (the `dirty` and btrfs-rw lines).";
            attribute :>> parent = "H.MEM.28";
            attribute :>> unit = ("user::vmo::Vmo::tracks_dirty", "user::vmo::Vmo::writable_page", "user::space::ask", "user::space::AddressSpace::read_only_paged");
        }

        requirement <'L.user.207'> aWriteBackAnswersWhatWasWritten : ItemLowLevel {
            attribute :>> statement = "begin_mapped_writes shall answer exactly the present Dirty pages, make them awaiting-clean, and take their translations, and only theirs, out of every mapping before it returns, with no shootdown when there are none.";
            attribute :>> criterion = "Of 8 pages the 2 written answered; their leaves absent, a page only read keeps its own, shootdowns advanced; none with nothing to do (the `dirty` line).";
            attribute :>> parent = "H.MEM.28";
            attribute :>> unit = ("user::vmo::Vmo::begin_mapped_writes");
        }

        requirement <'L.user.208'> aWriteDuringAWriteBackStays : ItemLowLevel {
            attribute :>> statement = "A write after begin_mapped_writes shall make its page Dirty again, and end_mapped_writes shall leave that page Dirty.";
            attribute :>> criterion = "The page written again is Dirty after the end and answered by the next begin (the `dirty` line).";
            attribute :>> parent = "H.MEM.28";
            attribute :>> unit = ("user::vmo::Vmo::end_mapped_writes");
        }

        requirement <'L.user.209'> aFailedWriteBackIsReportedAgain : ItemLowLevel {
            attribute :>> statement = "A write-back that failed from a page on shall leave those pages to be reported again, and with no memory for the list fsync shall answer ENOMEM with no page changed.";
            attribute :>> criterion = "end_mapped_writes with a failed page leaves it Dirty; fsync under an injected failure answers ENOMEM, the page Dirty, and the next writes it (the `dirty` and btrfs-rw lines).";
            attribute :>> parent = "H.MEM.28";
            attribute :>> unit = ("user::vmo::Vmo::end_mapped_writes", "user::vmo::Vmo::begin_mapped_writes");
        }

        requirement <'L.user.210'> reclaimTakesCleanMappedPages : ItemLowLevel {
            attribute :>> statement = "Reclaim shall take Clean pages of a sourced object whether or not a mapping may write it, and neither Dirty nor awaiting-clean ones; a page taken shall leave no state, so that one refilled starts Clean.";
            attribute :>> criterion = "Of three pages only the Clean one goes; a page cut and refilled reads Clean (the `dirty` line); stage 12's hook case (L.object.188).";
            attribute :>> parent = "H.MEM.28";
            attribute :>> unit = ("user::vmo::Pages::take_clean_into", "user::vmo::Pages::take_into", "user::vmo::Vmo::insert_absent");
        }

        requirement <'L.user.211'> aMappedWriteSurvivesAPowerCut : ItemLowLevel {
            attribute :>> statement = "A write through a shared mapping shall reach the disk across a power cut once fsync returned.";
            attribute :>> criterion = "test-powerfail's mapped round: every fourth body written through a shared mapping, its trailer's CRC judged after replay.";
            attribute :>> parent = "H.MEM.28";
            attribute :>> unit = ("user::vmo::Vmo::begin_mapped_writes");
        }

        requirement <'L.user.212'> aPinRefusesADiskFile : ItemLowLevel {
            attribute :>> statement = "vmo_pin shall refuse a pager's or a disk file's object with BAD_STATE, so that no device writes one of its pages unseen.";
            attribute :>> criterion = "A pin of a sourced object is BAD_STATE, where an anonymous one is given (the iommu line).";
            attribute :>> parent = "H.MEM.28";
            attribute :>> unit = ("syscall::native::unpaged_vmo_in");
        }

        requirement <'L.user.158'> aRegionByHandleKeepsItsCeiling : ItemLowLevel {
            attribute :>> statement = "A region vmo_map or space_map made shall record
                the most its handle allowed, readable always, writable only with
                WRITE and executable only with EXECUTE on the VMO handle, and the
                kernel's own code pages shall record that no call may change them;
                the Linux calls that reshape a region shall refuse every such
                region, as they refused vmo_map's.";
            attribute :>> criterion = "A protection past a region's ceiling is
                refused and one within it allowed (L.object.236's cases), and
                vmo_map's regions keep refusing mprotect and mremap (the native
                check's vmo_map case).";
            attribute :>> parent = "H.MEM.24";
            attribute :>> unit = ("user::space::AddressSpace::map_by_handle",
                "user::space::AddressSpace::map_object", "user::space::Ceiling::admits");
        }
        requirement <'L.user.159'> noRegionByHandleIsWritableAndExecutable : ItemLowLevel {
            attribute :>> statement = "The address space shall refuse, under its own
                lock, to map or protect a region by handle both writable and
                executable, whatever the handle carried; and no user root the
                stage 9 check reached shall hold a leaf both writable and
                executable.";
            attribute :>> criterion = "map_object asked for a writable and executable
                region with a ceiling allowing both is refused, and
                protect_by_handle asked the same is refused Beyond while read and
                execute is allowed; the user-root sweep counts L leaves, E > 0
                executable, 0 both (the `space` line).";
            attribute :>> parent = ("H.MEM.24", "H.MEM.4");
            attribute :>> unit = ("user::space::AddressSpace::map_by_handle",
                "user::space::AddressSpace::protect_by_handle",
                "user::space::Ceiling::admits",
                "user::space::AddressSpace::with_root_held");
        }
        requirement <'L.user.160'> aCloneByHandleCopiesOnWrite : ItemLowLevel {
            attribute :>> statement = "A clone by handle shall take the source's
                writable translations of its private pages out of the source's
                tables, and begin their shootdown, before it answers; after it,
                neither space shall see a write the other makes to private memory
                through a kernel copy, a page read-only at the clone and made
                writable after it included; memory mapped shared shall stay shared;
                and a page both hold shall go back to one holder as the clone goes.";
            attribute :>> criterion = "The source's leaf for a page written before
                the clone is writable before space_clone and not after it, and its
                shootdowns-begun count rose; writes by handle after the clone, by
                either side and to F-41's page on either side, are unseen by the
                other; a shared VMO's write is seen by both; a page both hold has
                two references, and one once the clone is closed. A program's own
                store through a stale translation is stage 6's USER_COW_PROGRAM
                check (H.MEM.8, L.user.61; F-41 itself is L.user.60). In user builds L.user.61 on Bare replaces that stage 6 check (6110 (7)).";
            attribute :>> parent = "H.MEM.25";
            attribute :>> unit = ("user::space::AddressSpace::fork",
                "user::space::AddressSpace::allocate_by_handle");
        }
        requirement <'L.user.161'> aCopyBetweenSpacesHonoursTheRegion : ItemLowLevel {
            attribute :>> statement = "A copy between two spaces by handle shall never
                hold both spaces' locks at once, shall write only through a writable
                region, copying a copy-on-write page first, and shall never make a
                region writable.";
            attribute :>> criterion = "A write by handle to a region made read-only
                is FAULT and the page keeps its byte; a write to a copy-on-write page
                after a clone gives the writer a copy (L.user.160's cases).";
            attribute :>> parent = "H.MEM.24";
            attribute :>> unit = ("syscall::native::space_write",
                "syscall::native::write_target", "syscall::native::space_read",
                "syscall::native::read_target");
        }
        requirement <'L.user.162'> anUnmapByHandleReachesARunningSpace : ItemLowLevel {
            attribute :>> statement = "An unmap or protect by handle of a space whose
                program runs on another processor shall take its translations down
                there, through the space's own shootdown, before it returns.";
            attribute :>> criterion = "A started process spinning in its text has its
                text page unmapped by its creator's handle from before the start,
                and ends killed by SIGSEGV within the check's patience.";
            attribute :>> parent = ("H.MEM.24", "H.MEM.17");
            attribute :>> unit = ("syscall::native::space_unmap",
                "user::space::AddressSpace::unmap");
        }
        requirement <'L.user.180'> aNormalRootsSlotsAreTheRestrictedRoots : ItemLowLevel {
            attribute :>> statement = "A normal root's restricted slots shall be the restricted root's or
                absent, and its region slots the region's, a restricted space's
                top tables never freed before it goes.";
            attribute :>> criterion = "check_normal_slots at the sweep; a control lets a top table free.";
            attribute :>> parent = "H.OBJ.26";
            attribute :>> unit = ("user::space::AddressSpace::sync_top",
                "user::space::AddressSpace::bind_region",
                "user::space::AddressSpace::check_normal_slots",
                "mm::copy_root_slot",
                "mm::allocate_root_for",
                "mm::free_root",
                "mm::root_slot_entry",
                "mm::unmap_in_keeping",
                "mm::ensure_top_in",
                "user::space::AddressSpace::new_region");
        }
        requirement <'L.user.181'> aRestrictedSpaceEndsAtTheRegion : ItemLowLevel {
            attribute :>> statement = "A restricted root shall hold no entry at or above SHARED_BASE, and
                a restricted space's ceiling shall be SHARED_BASE and shall not
                rise.";
            attribute :>> criterion = "The sweep; the check reads the ceiling; a control plants one.";
            attribute :>> parent = "H.TRAP.23";
            attribute :>> unit = ("user::space::AddressSpace::bind_region",
                "user::space::AddressSpace::flip_root",
                "user::space::AddressSpace::flip_root_on",
                "user::space::AddressSpace::root_for",
                "arch::x86_64::flip_user_root",
                "arch::aarch64::flip_user_root");
        }
        requirement <'L.user.182'> aPointerIsRoutedByTheMode : ItemLowLevel {
            attribute :>> statement = "A pointer at or above SHARED_BASE shall mean the region only from
                normal mode and only for the running task's own space.";
            attribute :>> criterion = "Cases 120 to 122.";
            attribute :>> parent = "H.OBJ.26";
            attribute :>> unit = ("user::space::AddressSpace::route",
                "user::space::AddressSpace::routed",
                "object::process::Process::caller_space");
        }
        requirement <'L.user.183'> aRegionShootdownReachesItsProcessors : ItemLowLevel {
            attribute :>> statement = "A change of a region's mappings shall reach every processor
                running a process of its partition in either mode.";
            attribute :>> criterion = "Case 89 with --smp 2 and up: the second process sees the new page.";
            attribute :>> parent = "H.OBJ.26";
            attribute :>> unit = "user::space::AddressSpace::install_as";
        }
        requirement <'L.user.193'> aRegionsProcessStartsOnlyShared : ItemLowLevel {
            attribute :>> statement = "PROCESS_START and PROCESS_RUN shall refuse a process of a
                region, BAD_STATE, from either mode: PROCESS_START_SHARED starts those.";
            attribute :>> criterion = "Case 153.";
            attribute :>> parent = "H.TRAP.21";
            attribute :>> unit = "syscall::native::start_with";
        }
        requirement <'L.user.189'> aMeasuredJobsRegionIsMeasured : ItemLowLevel {
            attribute :>> statement = "A region made for a measured job shall be measured, and K14's tests of a
                caller shall read the space its call means, the region's in normal mode, with
                the process's restricted space unmeasured by design.";
            attribute :>> criterion = "The sealing check's region_of_a_measured_job.";
            attribute :>> parent = "H.OBJ.26";
            attribute :>> unit = "syscall::native::region::region_create";
        }
        requirement <'L.user.184'> aRegionIsForkedByNothing : ItemLowLevel {
            attribute :>> statement = "SPACE_CLONE of a region's space shall be refused.";
            attribute :>> criterion = "The check.";
            attribute :>> parent = "H.OBJ.26";
            attribute :>> unit = "user::space::AddressSpace::fork";
        }
        requirement <'L.user.185'> noWriteRightUnderAHigherMapper : ItemLowLevel {
            attribute :>> statement = "A write right to a VMO a higher level maps shall not land at a
                lower level, but for the level declared.";
            attribute :>> criterion = "The `levels` line on every boot: the row's negative control.";
            attribute :>> parent = "H.OBJ.34";
            attribute :>> unit = ("user::vmo::Vmo::may_write_from",
                "user::vmo::Vmo::highest_mapper",
                "user::vmo::Vmo::set_creator_level");
        }
        requirement <'L.user.186'> noHigherMapOverALowerWriter : ItemLowLevel {
            attribute :>> statement = "A VMO a lower level has held a write right to shall not be mapped
                at a higher level, the target space's level, but for the level
                declared; a clone or a bind across levels is refused.";
            attribute :>> criterion = "The `levels` line on every boot.";
            attribute :>> parent = "H.OBJ.34";
            attribute :>> unit = "user::vmo::Vmo::may_map_at";
        }
        requirement <'L.user.187'> aLowerLevelIsNeverAPager : ItemLowLevel {
            attribute :>> statement = "A pager-backed VMO shall not be mapped above its pager's level,
                whatever is declared.";
            attribute :>> criterion = "By the same test as L.user.186; the pager is its creator, so its
                creator-level writer refuses first.";
            attribute :>> parent = "H.OBJ.34";
            attribute :>> unit = "user::vmo::Vmo::set_pager_level";
        }
        requirement <'L.user.188'> aDeclarationIsOneLevelOnce : ItemLowLevel {
            attribute :>> statement = "JOB_DECLARE_BUFFER shall need SET_LIMIT on the job and MAP on the
                VMO, be refused for a VMO declared, with a pager or mapped above,
                and lift the rule for its one level, audited.";
            attribute :>> criterion = "The `levels` line on every boot.";
            attribute :>> parent = "H.OBJ.34";
            attribute :>> unit = ("user::vmo::Vmo::declare_for",
                "syscall::native::job_declare_buffer");
        }
    }

    package PagerBackedObjects {
        doc /* src/kernel/src/object/pager.rs and the pager-backed half of
             * src/kernel/src/user/vmo.rs and user/space.rs: K3, pager-backed
             * VMOs (docs/microkernel/K3.md; MICROKERNEL.md section 3; the
             * consultant's OK IF, ledger 2858). An absent page of such an
             * object is its pager's: a fault on it, or a kernel copy into
             * it, sends the pager one page request over its port and waits,
             * bounded by the pager. Dirty tracking keeps a Clean page
             * read-only so that its first write is seen. The one
             * fault-forwarding mechanism NVIDIA.md section 11.4's windows
             * are built on. */

        requirement <'L.user.146'> anAbsentPagerPageIsAsked : ItemLowLevel {
            attribute :>> statement = "An absent page of a pager-backed VMO shall
                never be committed as zeros; a fault on it, or a kernel copy that
                may wait, shall open one request for the run of absent pages from
                it, at most 32, or join the open request of the same VMO, the same
                job and the same command that covers it, and a fault from another
                job shall open a request of its own.";
            attribute :>> criterion = "Stage 9's pager check: a read fault on page
                2 of 8 sends one packet for pages 2 to 7; two faults of one job on
                one page send one packet and both are resumed by its supply; two
                jobs' faults on one page send two packets.";
            attribute :>> parent = "H.MEM.22";
            attribute :>> unit = ("object::pager::PagerLink::request",
                "object::pager::PagerCore::list_or_join", "user::vmo::Vmo::absent_run",
                "user::vmo::Vmo::sourced", "user::space::AddressSpace::ask_pager",
                "user::space::AddressSpace::fault_with", "user::space::commit_page",
                "object::pager::Request::covers", "user::vmo::Vmo::pager",
                "user::vmo::Vmo::filler", "user::space::AddressSpace::paged_object_at",
                "user::space::ask", "user::space::permitted");
        }
        requirement <'L.user.147'> aRequestIsListedWithoutAllocating : ItemLowLevel {
            attribute :>> statement = "A request shall be opened with no address
                space, VMO or pager lock held; its record and its packet's room on
                the pager's port shall be had before the registry's lock is taken,
                listing it under that lock shall allocate nothing, and its packet
                shall be queued on the room promised once the lock is let go; a
                refusal of the record or the room shall be the fault's
                out-of-memory.";
            attribute :>> criterion = "Stage 9's pager check: every forwarded fault's
                packet arrives on the pager's port and the port loses none.";
            attribute :>> parent = "H.MEM.22";
            attribute :>> unit = ("object::port::Port::queue_promised",
                "object::pager::PagerCore::list_or_join", "object::pager::PagerLink::request");
        }
        requirement <'L.user.148'> aSuppliedFaultIsRetried : ItemLowLevel {
            attribute :>> statement = "A request shall end supplied when a supply
                makes its first page present, and its waiting threads shall retry
                the access, which then sees the bytes supplied.";
            attribute :>> criterion = "Stage 9's pager check: a fault resumed by a
                supply of page 2 reads the byte the pager wrote there, and its
                request is no longer outstanding.";
            attribute :>> parent = "H.MEM.22";
            attribute :>> unit = ("object::pager::PagerLink::supplied",
                "object::pager::PagerCore::end_where", "object::pager::take_ended",
                "object::pager::PagerLink::wait", "object::pager::PagerCore::leave");
        }
        requirement <'L.user.149'> aFailedFaultIsABusError : ItemLowLevel {
            attribute :>> statement = "A request its pager fails shall end its
                waiting threads' faults as unreadable, a SIGBUS to a program and an
                error to a copy, and shall be audited PAGER; a failure naming one
                request by its id shall end that request alone.";
            attribute :>> criterion = "Stage 9's pager check: a fault its pager fails
                is SIGBUS; with two jobs' requests on one page, failing one job's by
                its id ends that fault alone and the other job's is supplied
                after.";
            attribute :>> parent = "H.MEM.22";
            attribute :>> unit = ("object::pager::PagerLink::fail", "object::pager::record",
                "object::pager::Request::meets");
        }
        requirement <'L.user.150'> aWaitIsBounded : ItemLowLevel {
            attribute :>> statement = "A thread shall wait for its pager no longer
                than the pager's bound, and no wait shall end for the bound before
                it has passed; a wait that ends at the bound shall be a SIGBUS or
                an error, audited PAGER once for its request, and the last waiter
                to leave an open request shall end it.";
            attribute :>> criterion = "Stage 9's pager check: with a 5 ms bound and
                no answer, the fault is SIGBUS no sooner than 5 ms and within 5 s,
                and no request is left outstanding.";
            attribute :>> parent = "H.MEM.22";
            attribute :>> unit = ("object::pager::PagerLink::wait",
                "object::pager::PagerCore::leave", "object::pager::clamp_wait");
        }
        requirement <'L.user.151'> aKillEndsTheWait : ItemLowLevel {
            attribute :>> statement = "A thread waiting for its pager whose process
                is ending shall leave the wait at once, a program's fault returning
                with nothing installed; signals that do not end the process shall
                not end the wait.";
            attribute :>> criterion = "Stage 9's pager check: a client killed while
                its fault waits on a pager that never answers ends within 5 s, and
                its request is no longer outstanding.";
            attribute :>> parent = "H.MEM.22";
            attribute :>> unit = ("sched::work::own_word", "object::pager::PagerLink::wait");
        }
        requirement <'L.user.152'> aCopyWaitsOrIsRefused : ItemLowLevel {
            attribute :>> statement = "A kernel copy shall wait for a pager as a
                fault does, except into a VMO made with NO_COPY_WAIT or from a
                context that cannot block, where an absent page shall fail the copy
                at once and send nothing.";
            attribute :>> criterion = "Stage 9's pager check: a copy from an absent
                page waits for its supply and reads it; one from a NO_COPY_WAIT
                VMO's absent page fails at once with no packet.";
            attribute :>> parent = "H.MEM.22";
            attribute :>> unit = ("object::oom::user_fault", "syscall::native::copy_paged",
                "syscall::native::read_paged", "syscall::native::write_paged");
        }
        requirement <'L.user.153'> aSupplyMovesThePagersOwnPages : ItemLowLevel {
            attribute :>> statement = "pager_supply shall move only committed pages
                of an anonymous VMO that no device holds and no other object shares
                into the absent pages of the range, skipping present ones, which
                stay in the aux VMO; the moved pages shall leave every mapping of
                the aux VMO, with its shootdown, before they are the pager VMO's;
                and any refusal shall move nothing.";
            attribute :>> criterion = "Stage 9's pager check: a supply over a range
                whose second page is present leaves that page and its aux page as
                they were; a supply of a page another supply filled moves nothing;
                a supplied fault reads the aux bytes.";
            attribute :>> parent = "H.MEM.22";
            attribute :>> unit = ("user::vmo::Vmo::supply_from", "user::vmo::Vmo::absent_in",
                "user::vmo::Vmo::take_for_supply", "user::vmo::Vmo::put_supplied");
        }
        requirement <'L.user.154'> aCleanPageIsNeverWritable : ItemLowLevel {
            attribute :>> statement = "A Clean page of a pager-backed VMO shall
                never be mapped writable nor written in place by a kernel copy; its
                first write shall mark it Dirty, or, in a trap-dirty VMO, send a
                dirty request that PAGER_OP DIRTY lets through and FAIL refuses,
                the page then staying Clean; a kernel write into it shall mark it
                Dirty.";
            attribute :>> criterion = "Stage 9's pager check: a write to a Clean
                trap-dirty page asks the pager, lands once DIRTY answers, and the
                query shows it alone Dirty; a refused one is SIGBUS and its page
                stays Clean; a read leaves a page mapped read-only, and a write of
                an untrapped page marks it Dirty with no packet and maps it
                writable.";
            attribute :>> parent = "H.MEM.23";
            attribute :>> unit = ("user::vmo::Vmo::writable_page", "user::vmo::Vmo::mark_dirty",
                "user::vmo::Vmo::write_paged", "user::vmo::Vmo::page_state",
                "user::vmo::state_of", "user::space::AddressSpace::read_only_paged",
                "user::space::writable_in_place", "user::space::writable_flags",
                "user::space::writable_in",
                "user::vmo::Vmo::dirty_range", "object::pager::PagerLink::dirtied");
        }
        requirement <'L.user.155'> aWriteBackKeepsLaterWrites : ItemLowLevel {
            attribute :>> statement = "PAGER_OP WRITEBACK_BEGIN shall make the
                range's Dirty pages awaiting-clean and return only once no
                processor holds a writable translation of the range;
                WRITEBACK_END shall clean only awaiting-clean pages; a write
                between them shall make its page Dirty again; and DECOMMIT shall
                take Clean pages only.";
            attribute :>> criterion = "Stage 9's pager check: after BEGIN the page
                is no longer mapped writable; a page written after BEGIN is still
                Dirty after END while the other is Clean; DECOMMIT takes the Clean
                page and leaves the Dirty one.";
            attribute :>> parent = "H.MEM.23";
            attribute :>> unit = ("user::vmo::Vmo::writeback_begin",
                "user::vmo::Vmo::writeback_end", "user::vmo::Vmo::decommit_clean",
                "user::vmo::Vmo::dirty_runs");
        }
        requirement <'L.user.157'> theFaultingJobPaysThroughItsTicket : ItemLowLevel {
            attribute :>> statement = "Each page request shall carry a ticket the kernel
                issued for the opening thread's process and job, adoptable only through
                its pager's handle with PAGER and only while the request is
                outstanding; pages the adopted pager commits and supplies shall stay
                charged to that job, on its reservation where it has one. At the job's
                object limit the fault shall end SIGBUS or FAULT with no pager asked; a
                pager may spend the job's limit and reservation while a request is open,
                a request a keeper keeps across its pager's close included: the ticket
                stays live and adoptable through the next instance, and a thread of the
                closed instance that adopted it goes on charging that job until the
                request ends.";
            attribute :>> criterion = "Stage 9's pager check, case o: the page is the
                faulting job's alone and drawn from its reservation, the pager's job
                paying nothing; another pager's handle, a handle without PAGER and a
                request ended all adopt nothing. The rebind check's second cycle: an
                instance adopts a request's ticket and closes unanswered, and the
                next adopts the same ticket by the id sent again.";
            attribute :>> parent = "H.MEM.22";
            attribute :>> unit = ("object::pager::PagerCore::adoptable_ticket",
                "object::ticket::issue_for", "syscall::native::adopt_ticket");
        }
        requirement <'L.user.156'> aPagersCloseEndsItsFaults : ItemLowLevel {
            attribute :>> statement = "The close of a pager's handle, or DETACH,
                run where it may block, shall end every outstanding request of its
                VMOs at once, audited, refuse every later request, and leave the
                present pages mapped and usable.";
            attribute :>> criterion = "Stage 9's pager check: a fault waiting on a
                pager whose handle closes is SIGBUS well within its bound; a later
                fault on an absent page is SIGBUS with no packet; a present page
                still reads.";
            attribute :>> parent = "H.MEM.22";
            attribute :>> unit = ("object::pager::Pager::drop", "object::pager::PagerCore::close",
                "object::pager::PagerLink::detach", "object::pager::PagerLink::is_gone");
        }
        requirement <'L.mm.111'> sealOnlyPlain : ItemLowLevel {
            attribute :>> statement = "A seal shall need READ, MAP and WRITE on the handle and shall
                refuse a VMO that is pager-backed, a file's, physical,
                coherent, combining or holding a kernel view.";
            attribute :>> criterion = "object::sealing_check: a coherent VMO, a kernel view and a
                read-only handle refused; with the kind's test removed it
                fails.";
            attribute :>> parent = "H.MEM.29";
            attribute :>> unit = "user::vmo::Vmo::seal";
        }
        requirement <'L.mm.112'> sealRefusedWhileWritable : ItemLowLevel {
            attribute :>> statement = "A seal shall refuse a VMO with a region by handle whose
                ceiling holds WRITE, a file mapping that may write, a live
                hold, or a frame with a second reference; the count of such
                regions shall fall only after that unmap's shootdown.";
            attribute :>> criterion = "object::sealing_check: each case refused and, once unmapped,
                sealed; with the count's test removed it fails.";
            attribute :>> parent = "H.MEM.29";
            attribute :>> unit = ("user::vmo::Vmo::seal",
                "user::vmo::Vmo::raise_writable_region",
                "user::vmo::Vmo::lower_writable_region");
        }
        requirement <'L.mm.113'> sealedNeverChanges : ItemLowLevel {
            attribute :>> statement = "After a seal every path that changes a page or the page set
                shall refuse, and each lock of a VMO's pages shall say what it
                is to a seal.";
            attribute :>> criterion = "object::sealing_check drives vmo_write and a writable map
                through a kept handle and each path by name, and reads the
                bytes back; check-vmo-seal-tags.py fails on an untagged lock,
                with a planted control.";
            attribute :>> parent = "H.MEM.29";
            attribute :>> unit = ("user::vmo::Vmo::write_page",
                "user::vmo::Vmo::commit_and_write",
                "user::vmo::Vmo::zero_from",
                "user::vmo::Vmo::hold",
                "user::vmo::Vmo::hold_read");
        }
        requirement <'L.mm.114'> digestOfLengthAndFrames : ItemLowLevel {
            attribute :>> statement = "A seal's digest shall be SHA-256 of the object's length in
                bytes, little-endian, and its frames in page order.";
            attribute :>> criterion = "object::sealing_check against a vector computed on the host,
                and a byte's difference; with the length left out it fails.";
            attribute :>> parent = "H.MEM.29";
            attribute :>> unit = "user::vmo::Vmo::seal";
        }
        requirement <'L.mm.115'> nothingRunsBeforeItsDigest : ItemLowLevel {
            attribute :>> statement = "Between the freeze and the digest's store vmo_digest shall
                answer SHOULD_WAIT and an executable map BAD_STATE.";
            attribute :>> criterion = "object::sealing_check on an object frozen for the check; with
                the test removed it fails.";
            attribute :>> parent = "H.MEM.30";
            attribute :>> unit = ("syscall::native::vmo_digest",
                "user::vmo::Vmo::freeze_for_check",
                "user::space::AddressSpace::map_by_handle");
        }
        requirement <'L.mm.116'> measuredIsStickyAndInherited : ItemLowLevel {
            attribute :>> statement = "A job made with JOB_MEASURED, and every job made inside it,
                shall be measured, and no call shall clear it.";
            attribute :>> criterion = "object::sealing_check; with the inheritance removed it fails.";
            attribute :>> parent = "H.MEM.30";
            attribute :>> unit = ("object::job::Job::make_measured",
                "object::job::Job::measured");
        }
        requirement <'L.mm.117'> measuredMapOnlySealed : ItemLowLevel {
            attribute :>> statement = "In a measured space space_map with MAP_EXECUTE, or through a
                handle carrying EXECUTE, shall take only a sealed VMO whose
                digest is stored, and answer BAD_STATE otherwise with an
                UNMEASURED record.";
            attribute :>> criterion = "object::sealing_check; with the test removed it fails, and the refusal's record read from the ring.";
            attribute :>> parent = "H.MEM.30";
            attribute :>> unit = ("user::space::AddressSpace::map_by_handle", "syscall::native::space_map");
        }
        requirement <'L.mm.118'> measuredNoExecutableAnonymous : ItemLowLevel {
            attribute :>> statement = "In a measured space space_allocate with MAP_EXECUTE shall
                answer BAD_STATE, and its regions' ceiling shall hold no
                EXECUTE.";
            attribute :>> criterion = "object::sealing_check; with the test removed it fails.";
            attribute :>> parent = "H.MEM.30";
            attribute :>> unit = "user::space::AddressSpace::allocate_by_handle";
        }
        requirement <'L.mm.119'> measuredProtectWithinSealed : ItemLowLevel {
            attribute :>> statement = "In a measured space space_protect to MAP_EXECUTE shall pass
                only a region whose ceiling holds EXECUTE, which only a sealed
                map has.";
            attribute :>> criterion = "object::sealing_check on anonymous memory; with the ceiling
                widened it fails.";
            attribute :>> parent = "H.MEM.30";
            attribute :>> unit = "syscall::native::space_protect";
        }
        requirement <'L.mm.120'> measuredNoPlainExecutable : ItemLowLevel {
            attribute :>> statement = "A measured caller's plain vmo_executable shall answer
                BAD_STATE.";
            attribute :>> criterion = "object::sealing_check; with the test removed it fails.";
            attribute :>> parent = "H.MEM.30";
            attribute :>> unit = "syscall::native::vmo_executable";
        }
        requirement <'L.mm.121'> measuredCreateOnlySealed : ItemLowLevel {
            attribute :>> statement = "process_create into a measured job shall take only a sealed
                image, measure the new process's space and record the image's
                digest.";
            attribute :>> criterion = "object::sealing_check's refusal of an unsealed image; with the
                test removed it fails.";
            attribute :>> parent = "H.MEM.30";
            attribute :>> unit = ("syscall::native::process_create",
                "user::space::AddressSpace::note_image",
                "user::space::Inner::note_image");
        }
        requirement <'L.mm.122'> cloneDoesNotLaunder : ItemLowLevel {
            attribute :>> statement = "A measured caller's space_clone of an unmeasured space shall
                answer BAD_STATE, and a clone shall keep its source's measured
                state and record.";
            attribute :>> criterion = "object::sealing_check; with the test removed it fails.";
            attribute :>> parent = "H.MEM.30";
            attribute :>> unit = ("syscall::native::space_clone",
                "user::space::AddressSpace::fork");
        }
        requirement <'L.mm.124'> digestsKept : ItemLowLevel {
            attribute :>> statement = "A space shall record the digest of each sealed VMO it maps
                executable, once, up to MAX_IMAGES, keep it across an unmap
                and copy it across a clone.";
            attribute :>> criterion = "object::sealing_check; with an unmap removing it the check
                fails.";
            attribute :>> parent = "H.MEM.30";
            attribute :>> unit = ("user::space::Images::note",
                "user::space::AddressSpace::images_into");
        }
        requirement <'L.mm.125'> partialListSaysSo : ItemLowLevel {
            attribute :>> statement = "process_images shall answer the digests' count with
                IMAGES_UNMEASURED set when the space is not measured.";
            attribute :>> criterion = "object::sealing_check; with the bit removed it fails.";
            attribute :>> parent = "H.MEM.30";
            attribute :>> unit = "syscall::native::process_images";
        }
        requirement <'L.mm.126'> noMoveAcrossTheLine : ItemLowLevel {
            attribute :>> statement = "A process shall cross between a measured and an unmeasured job
                by no move, either way; process_create's placement of a new
                process excepted.";
            attribute :>> criterion = "object::sealing_check; with the test removed it fails.";
            attribute :>> parent = "H.MEM.30";
            attribute :>> unit = "object::job::Job::measure_refuses";
        }
        requirement <'L.mm.127'> thePassIsOfSpaceAndList : ItemLowLevel {
            attribute :>> statement = "A process shall pass K14's test only if its space is measured,
                untainted, and every digest on its record is on the certified list.";
            attribute :>> criterion = "object::grant_check: a space with an unlisted digest does not pass.";
            attribute :>> parent = "H.MEM.30";
            attribute :>> unit = ("user::space::AddressSpace::passes", "user::space::set");
        }
        requirement <'L.mm.128'> aChangeByAnotherTaints : ItemLowLevel {
            attribute :>> statement = "A change to a space by a caller that does not pass, before or after
                the start, shall taint it for good.";
            attribute :>> criterion = "object::grant_check.";
            attribute :>> parent = "H.MEM.30";
            attribute :>> unit = ("syscall::native::reach_into", "user::space::AddressSpace::reached");
        }
        requirement <'L.mm.129'> noSupervisorOutside : ItemLowLevel {
            attribute :>> statement = "A passing process shall have no supervisor that does not pass, on
                itself, its job or an ancestor.";
            attribute :>> criterion = "object::grant_check.";
            attribute :>> parent = "H.MEM.30";
            attribute :>> unit = ("object::job::Job::note_grant", "object::job::Job::supervised_from_outside");
        }
        requirement <'L.mm.130'> aGrantHoldsAfterIt : ItemLowLevel {
            attribute :>> statement = "After a grant the node's holder shall not lose the test by a later act
                of anyone but itself without its grant ending.";
            attribute :>> criterion = "object::grant_check.";
            attribute :>> parent = "H.MEM.30";
            attribute :>> unit = "object::job::Job::note_grant";
        }
        requirement <'H.MEM.32'> noSharedHeapAfterTheSeal : ItemHighLevel {
            attribute :>> statement = "After the seal the kernel's global allocator shall serve a job only from the
                retyped pages of its own promise, a task with no job only from the named kernel pool, and refuse
                every other request.";
            attribute :>> criterion = "A personality=user kernel_memory=retyped boot's mm::seal::check, and
                test-rustc, test-btrfsd-restart, test-partitions under it reporting zero refused.";
            attribute :>> parent = ("O.CAPABILITY", "ASR-3");
            attribute :>> scope = "kernel_memory=retyped";
        }
    }
}
