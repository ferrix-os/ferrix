/*
 * Ferrix — SysML v2 model, part 8: devices and userspace drivers.
 *
 * docs/ARCHITECTURE.md §7. The kernel enumerates buses because that needs
 * ACPI or a device tree and privileged access; it does not drive devices.
 * Everything from the device node outward is stage 10, which is done: the
 * drivers are processes devmgr starts. What it still owes is named on the
 * part that owes it.
 */
package FerrixDrivers {
    private import ScalarValues::*;
    private import FerrixLifecycle::*;
    private import FerrixObjects::*;
    private import FerrixMemory::Vmo;

    // -----------------------------------------------------------------------
    // Reaching the machine's description, today
    // -----------------------------------------------------------------------

    #implemented part def AcpiAccess {
        @stage { number = 3; }
        doc /* src/kernel/src/discovery/acpi.rs: the one place a physical address firmware
             * wrote becomes a reference the parser reads, through the direct
             * map, refusing addresses or lengths outside it. src/lib/platform/acpi never
             * dereferences a pointer: RSDP, XSDT/RSDT, MADT, FADT fixed
             * fields, GTDT, HPET, and for stage 10 the MCFG, GICv2m frames,
             * the DMAR and the IORT. No AML. */
        action open;
        action madt;
        action fadt;
        action gtdt;
        action hpet;
    }

    #implemented part def FdtAccess {
        @stage { number = 1; }
        doc /* src/kernel/src/discovery/fdt.rs: the loader's copy of firmware's tree, read
             * through the direct map from DeviceTree memory that nothing
             * reclaims, so the borrow is honestly 'static. src/lib/platform/fdt: nodes,
             * properties, reg, interrupts, compatible, stdout-path, the
             * interrupt controller, the timer, /cpus, the PSCI conduit. */
        action open;
        action console;
        action interruptController;
        action timer;
        action cpus;
        action psci;
    }

    #implemented part def MmioWindows {
        @stage { number = 3; }
        doc /* src/kernel/src/mmio.rs: the one place that says read_volatile and
             * write_volatile. A window with no base reads zero and discards
             * writes, so "never mapped" is a value rather than a null
             * dereference. */
        action read32;
        action write32;
    }

    // -----------------------------------------------------------------------
    // Stage 10
    // -----------------------------------------------------------------------

    #implemented part def DeviceNode {
        @stage { number = 10; }
        doc /* What the kernel creates per device found, and hands devmgr a
             * handle to. src/kernel/src/device.rs: one per PCI function and per
             * virtio,mmio tree node, published at boot. Apertures and vectors
             * are Aperture and Vector tokens only this module mints, and
             * IoMapping and Interrupt take those rather than numbers, so a
             * driver cannot name memory or an interrupt its device does not
             * have. The pages of a PCI function's MSI-X table and pending-bit
             * array are withheld from its apertures. A PCI function's vectors
             * are its MSI-X entries, minted on first ask and masked at the
             * entry's own bit. device_info writes what a driver needs to
             * find its registers, and each node has the IOMMU domain its
             * DMA goes through. */
        attribute compatible : String;
        attribute mmioWindows : Natural[0..*];
        attribute interrupts : Natural[0..*];
    }

    #implemented part def DeviceEnumeration {
        @stage { number = 10; }
        doc /* ACPI on x86-64 and AArch64 under EDK2, device tree on ARMv7-A
             * and where AArch64 firmware offers one; PCIe bus walk from
             * either. src/kernel/src/discovery/pci.rs: MCFG (src/lib/platform/acpi) or
             * pci-host-ecam-generic (src/lib/platform/fdt), ECAM mapped a bus at a time,
             * the src/lib/platform/pci walk with every BAR sized and every capability
             * list walked, in the boot test on all three architectures.
             * Device nodes are built from what it finds: see DeviceNode.
             * Owed after the exit: trusting a BAR firmware placed but left
             * decoding off, of which only the device tree's host-bridge
             * windows are read so far. */
        ref part acpi : AcpiAccess[0..1] {
            doc /* The MCFG, on ACPI machines. */
        }
        ref part fdt : FdtAccess[0..1] {
            doc /* pci-host-ecam-generic and virtio,mmio nodes, on tree machines. */
        }
        ref part ecam : MmioWindows {
            doc /* Configuration space, a bus at a time. */
        }
        part nodes : DeviceNode[0..*];
        action enumerate;
    }

    #implemented part def IommuDomain {
        @stage { number = 10; }
        doc /* Scoped to one device: the device addresses a DMA VMO gets come
             * from here, so a driver cannot DMA over the kernel or over
             * another driver. src/kernel/src/iommu.rs's Domain, one per device
             * node, made the first time it is asked for: a pin gives each
             * page a device address and an unpin takes them back. A
             * translated domain maps each pinned page at its own physical
             * address and nothing else; an untranslated one, where no unit
             * translates, hands out physical addresses. */
        ref part device : DeviceNode;
        action mapForDevice;
        action unmapForDevice;
    }

    enum def IommuMode {
        Enforced;   // VT-d, AMD-Vi, SMMUv3
        DegradedTrusted;  // no IOMMU: announced loudly at boot
    }

    #implemented part def IommuDomains {
        @stage { number = 10; }
        doc /* Where the hardware is: src/lib/platform/acpi's dmar module (VT-d units
             * and their device scopes) and iort module (root complex to
             * SMMUv3 stream IDs), tested against QEMU's own table builders,
             * and the device tree's arm,smmu-v3 nodes and iommu-map.
             * src/kernel/src/iommu.rs places every PCI function behind a unit
             * before any is programmed, counting what it cannot follow as
             * unresolved rather than bypassing. VT-d on x86-64 and the
             * SMMUv3 under ACPI on AArch64 translate from before PCI
             * enumeration, and a deliberate out-of-domain write faults on
             * both in every boot test. ARMv7-A stays in degraded trusted
             * mode, announced at boot. AMD-Vi is not driven. */
        attribute mode : IommuMode;
        ref part acpi : AcpiAccess[0..1] {
            doc /* The DMAR (VT-d) and the IORT (SMMUv3). */
        }
        ref part fdt : FdtAccess[0..1] {
            doc /* arm,smmu-v3 nodes and iommu-map. */
        }
        part domains : IommuDomain[0..*];
    }

    #implemented part def DriverProcess {
        @stage { number = 10; }
        doc /* An ordinary user process in its own Job, holding exactly the
             * capabilities devmgr gave it. A driver fault is a process fault;
             * a wedged driver is a Job kill. Twelve exist, native programs on
             * src/user/system/native/rt under /lib/drivers: virtio-blk,
             * stm32-sdmmc, nvme, virtio-net, virtio-gpu, stm32-ltdc, gc400,
             * virtio-input, usbhid, usbdev, virtio-snd and vport, each a thin
             * layer of handles over its src/lib/ crates. */
        ref part device : DeviceNode {
            doc /* The one node devmgr handed it: every aperture and vector it
                 * holds is minted from this node. */
        }
        ref part domain : IommuDomain {
            doc /* The device's domain, which gives dmaBuffers their device
                 * addresses. */
        }
        ref part job : Job;
        part ioMappings : IoMapping[0..*] {
            doc /* One per BAR or MMIO window, and nothing outside it. */
        }
        part interrupts : Interrupt[0..*] {
            doc /* One per vector, bound to a Port. */
        }
        part eventPort : Port;
        ref part dmaBuffers : Vmo[0..*] {
            doc /* Device addresses from the device's IOMMU domain. */
        }
        part channel : Channel {
            doc /* To the kernel subsystem it serves: block, display, net, input. */
        }
        part ring : SharedRing;
    }

    #implemented part def SharedRing {
        @stage { number = 10; }
        doc /* The data path is not per-request IPC: driver and kernel share
             * a descriptor ring in a VMO and ring a doorbell; requests batch.
             * The same shape virtio and NVMe already use. src/lib/drivers/virtio's split
             * virtqueue (driver and device halves, over abstract shared
             * memory) is the first of these. Between kernel and driver:
             * src/lib/proto/blkring (docs/BLOCK-RING.md) and src/lib/proto/netring
             * (docs/NET-RING.md), with src/kernel/src/interfaces/block_ring and
             * src/kernel/extensions/device/net-ring/src/interfaces/net_ring as the kernel's
             * ends and doorbells as port packets. The display and input drivers need none: frames do
             * not move, and their control channels carry the rest. */
        ref part memory : Vmo;
        action addChain;
        action takeUsed;
        action doorbell;
    }

    #implemented part def DevMgr {
        @stage { number = 10; }
        doc /* A native program on src/user/system/native/rt, not a musl binary: src/user/system/native/devmgr,
             * /sbin/devmgr. Receives a handle per device node, matches a
             * driver, spawns it in its own Job with the four resources
             * above. The kernel starts it from stage 10's boot check with
             * DEVICES messages holding a job, every device node twice and
             * every image /lib/drivers/MANIFEST lists -- the drivers, and
             * drvupdated in the images that carry it (DrvUpdated below) --
             * (src/kernel/src/discovery/devmgr.rs, src/lib/proto/devmgr-proto); it matches
             * virtio-blk, virtio-net, virtio-gpu, virtio-input and the
             * virtio-serial port by a table of its own, starts each driver
             * with START, waits for every one but the port driver to be
             * PUBLISHED before the next, and REPORTs. docs/DEVMGR.md. */
        ref part nodes : DeviceNode[0..*] {
            doc /* A handle per node, from the kernel's DEVICES messages. */
        }
        ref part drivers : DriverProcess[0..*] {
            doc /* Each started in a Job devmgr made, on one of nodes. */
        }
        ref part updater : DrvUpdated[0..1] {
            doc /* Started from /lib/drivers when the image carries it. */
        }
        action match;
        action spawnDriver;
        #implemented action quiesceOnDeath {
            doc /* device_quiesce after a driver's TERMINATED: the kernel waits
                 * for the block, display and render cores to let the device go
                 * (src/kernel/src/claim.rs), then DIED. */
        }
        #inProgress action updateDriver {
            doc /* An image root sent through drvupdated put on a device that
                 * a restartDriver kind drives: devmgr copies it, proves it
                 * loads with process_create in a scratch job, stops and
                 * quiesces the running driver, starts the copy and gives it
                 * 15 s to publish, or starts the image the device had again.
                 * The display kind is gated by test-restart --update; the
                 * other kinds and the image's signature (D3) are owed.
                 * docs/DEVMGR.md section 4.1. */
        }
        #implemented action restartDriver {
            doc /* A display driver that died is started again on a duplicate
                 * of devmgr's kept device handle, at most eight times a device;
                 * its card returns as the number it had. RESTARTED tells the
                 * kernel. docs/DEVMGR.md section 4. */
        }
    }

    #inProgress part def DrvUpdated {
        @stage { number = 10; }
        doc /* src/user/system/native/drvupdated: the helper through which a
             * new driver image reaches DevMgr, which reads no files and waits
             * on one port. Started by devmgr from /lib/drivers when the image
             * carries it -- only test-restart --update's do (SAFETY-MANUAL
             * AoU-26) -- it takes root's connections on the abstract socket
             * ferrix.devmgr.update, refuses any other peer and any header past
             * 8 MiB before it makes a VMO, and hands devmgr the request and
             * the image's VMO on a channel. /bin/drvupdate is its client.
             * docs/DEVMGR.md section 4.1. */
        ref part devmgr : DevMgr {
            doc /* The one peer it hands a request and an image VMO to. */
        }
    }

    #implemented part def VirtioBlkDriver :> DriverProcess {
        @stage { number = 10; }
        doc /* The first driver: virtio-blk as a user process. Exit test: a
             * sector read through ring 3 with the IOMMU on, and a deliberate
             * out-of-domain DMA attempt faulting. src/user/system/native/drivers/block/virtio-blk over
             * src/lib/drivers/block/virtio-blk and src/lib/drivers/block/blkserve; the exit is met in the boot
             * test, with VT-d translating on x86-64 and the SMMUv3 on
             * AArch64, and ARMv7-A in degraded trusted mode. */
    }

    #implemented part def VirtioNetDriver :> DriverProcess {
        doc /* src/user/system/native/drivers/net/virtio-net over src/lib/drivers/net/virtio-net and src/lib/drivers/net/netserve, speaking the
             * net ring; cargo xtask test-net is its gate. */
    }

    #implemented part def VirtioGpuDriver :> DriverProcess {
        @stage { number = 17; }
        doc /* src/user/system/native/drivers/display/virtio-gpu over src/lib/drivers/display/virtio-gpu: the display core's card0 over
             * displayctl, and since stage 19 the render core's renderD128
             * over renderctl, turning its messages into virtio-gpu's 3D
             * commands. cargo xtask test-display is its gate. The one driver
             * devmgr starts again after it dies (restartDriver). */
    }

    #implemented part def VirtioInputDriver :> DriverProcess {
        @stage { number = 17; }
        doc /* src/user/system/native/drivers/input/virtio-input over src/lib/drivers/input/virtio-input, feeding the input core's
             * /dev/input/eventN over inputctl; cargo xtask test-input is its
             * gate. */
    }

    #implemented part def UsbHidDriver :> DriverProcess {
        @stage { number = 17; }
        doc /* src/user/system/native/drivers/usb/usbhid over src/lib/drivers/usb/usb-host: the STM32MP157's EHCI
             * controller, its hubs, and HID keyboards, mice and media keys
             * read by their report descriptors, each served to the input
             * core over a control channel of its own, keyboards' LEDs lit
             * by the core's STATUS.
             * devmgr starts it as a bus host and does not wait for it; its
             * memory is pinned PIN_COHERENT. No QEMU machine has the
             * device, so no boot test exercises it: its gates are
             * src/lib/drivers/usb/usb-host's tests against a model of EHCI and the board's
             * bus, and it ran on the DK1 on 2026-09-23 (docs/INPUT.md §7).
             * Since 2026-10-10 it also drives a PC's xHCI controller, picked
             * by what START names (docs/XHCI.md; a bulk-only disk is read and
             * not yet served to the block core), gated under QEMU by cargo
             * xtask test-usb; a USB keyboard worked on the N150 box on
             * 2026-10-15.
             * Since 2026-10-25 a tablet's absolute axes reach the input
             * core as ABS_X, ABS_Y and ABS_WHEEL with the HID field's
             * range (test-usb attaches a usb-tablet and requires two
             * places); and the boot word ferrix.usbhid.reports, or the
             * file /run/usbhid-reports, makes it log each interrupt report
             * of the functions named at debug (docs/XHCI.md section 13). */
    }

    #inProgress part def Gc400Driver :> DriverProcess {
        @stage { number = 19; }
        doc /* src/user/system/native/drivers/gpu/gc400 over src/lib/drivers/gpu/gc400: the STM32MP157's Vivante GC400T,
             * the G2 step of the board's gears (docs/GPU.md §6.3). It
             * prints the core's identity, soft-resets and initialises it as
             * etnaviv does, starts the front end on a WAIT/LINK loop in one
             * page pinned PIN_COHERENT, splices in two blocks that each
             * raise an event, and takes each as the interrupt. devmgr starts
             * it as an engine, which serves no kernel subsystem yet, and does
             * not wait for it. No QEMU machine has the core; its gates are
             * src/lib/drivers/gpu/gc400's tests against models of the host interface and
             * the front end, and on the board, on 2026-09-24, both events
             * arrived by interrupt (G2 done). Drawing is G3 to G5. */
    }

    #inProgress part def Stm32SdmmcDriver :> DriverProcess {
        @stage { number = 10; }
        doc /* src/user/system/native/drivers/block/stm32-sdmmc over
             * src/lib/drivers/block/stm32-sdmmc: the STM32MP157's SDMMC1 as
             * a disk behind the block ring, so the kernel's GPT scan publishes
             * the card's partitions and btrfs mounts from one (docs/CHROME.md
             * 10.1). The kernel publishes the controller as a device tree node
             * and writes none of its registers: U-Boot left it running. The
             * driver moves every word through the FIFO with hardware flow
             * control and never turns the internal DMA on, and serves a write
             * only inside a partition named ferrix-*. Its gates are the
             * library's host tests against a model of the controller and a
             * card, and the boot check of the one tree disk; no emulator has
             * the controller, and it has not run on the board (2026-10-08). */
    }

    #inProgress part def NvmeDriver :> DriverProcess {
        @stage { number = 10; }
        doc /* src/user/system/native/drivers/block/nvme over
             * src/lib/drivers/block/nvme: an NVM Express controller's first
             * namespace as a disk behind the block ring (docs/NVME.md), the
             * first driver for a disk a PC has. devmgr starts it on any
             * function of class code 01:08:02; the kernel is not changed.
             * It resets and enables the controller, transfers straight into
             * the ring's data region through PRP lists, lends a drive
             * without DRAM its host memory buffer, aborts and resets on a
             * command that does not come back, and notifies the controller
             * before it disables it. Its gates are the library's host tests
             * against a model of a controller, and cargo xtask test-nvme on
             * QEMU's emulated one, with / on a drive below a PCIe switch. It
             * has since driven a real WD SN720 through VFIO and installed
             * Ferrix onto it (the customer's word, 2026-10-21). */
    }

    #inProgress part def AhciDriver :> DriverProcess {
        @stage { number = 10; }
        doc /* src/user/system/native/drivers/block/ahci over
             * src/lib/drivers/block/ahci: a SATA disk behind an AHCI
             * controller as a disk behind the block ring (docs/AHCI.md), for
             * the customer's N150 box. devmgr starts it on class code
             * 01:06:01 of any vendor. The controller is brought up polled
             * (COMRESET of a link firmware left down, a busy device waited
             * for, a refused IDENTIFY said), and each block-ring request is
             * carried out whole by one transfer. A controller with no ATA
             * disk is nothing to serve, not a failed driver. Its gates are
             * the library's tests against a model HBA and cargo xtask
             * test-n150-sata on QEMU's q35 controller; it served the box's
             * drive on 2026-10-15. */
    }

    #inProgress part def Yt6801Driver :> DriverProcess {
        @stage { number = 10; }
        doc /* src/user/system/native/drivers/net/yt6801 over
             * src/lib/drivers/net/yt6801 and src/lib/drivers/net/dwmac: the
             * Motorcomm YT6801, the N150 box's gigabit port (networking
             * page), speaking the net ring under ferrix-netserve's loop.
             * devmgr starts it on 1F0A:6801. The kernel holds the function's
             * MSI-X off and grants its table page (L.device.35-37). Its
             * gates are the libraries' tests against models of the chip and
             * the DesignWare core, and a QEMU e1000e for the kernel change;
             * on the box on 2026-10-15 the link came up at one gigabit, and
             * the driver polls every millisecond until its one MSI arrives,
             * which it does rarely (docs/BACKLOG.md). */
    }

    #inProgress part def Rtl8169Driver :> DriverProcess {
        @stage { number = 10; }
        doc /* src/user/system/native/drivers/net/rtl8169 over
             * src/lib/drivers/net/rtl8169: Realtek's RTL8111H (8168H, XID
             * 0x541), nazuna's onboard gigabit port (networking page),
             * speaking the net ring under ferrix-netserve's loop. devmgr
             * starts it on 10EC:8168 and the driver refuses any other XID.
             * No kernel change: registers in BAR 2, MSI-X table in BAR 4.
             * Its gates are the library's tests against a model of the chip
             * and cargo xtask check; QEMU models no 8168. On 2026-10-24 it
             * drove the real chip through vfio in a KVM guest: link at one
             * gigabit, DHCP, ping, TCP at 235 to 405 Mbit/s. */
    }

    #inProgress part def EfifbDriver :> DriverProcess {
        @stage { number = 21; }
        doc /* src/user/system/native/drivers/display/efifb: the firmware's
             * framebuffer as the display core's card0, for a PC whose GPU has
             * no driver (docs/DISPLAY.md section 8). Under the kernel option
             * ferrix.efifb the last finder lends the framebuffer to a node of
             * its own, write-combining from its first map, and the driver
             * copies each flushed rectangle onto it; hyprix composites into
             * dumb buffers as on virtio-gpu. Its gate is cargo xtask
             * test-compositor --boot firmware-screen; hyprix drew on the N150
             * box's framebuffer on 2026-10-15. */
    }

    #inProgress part def IntelGpuDriver :> DriverProcess {
        @stage { number = 21; }
        doc /* src/user/system/native/drivers/gpu/intel over
             * src/lib/drivers/gpu/intel-xelp: a render driver for the N150's
             * Xe-LP graphics (docs/INTEL-GPU.md), following i915 file by
             * file. The library is the i915 uAPI front end over a back end,
             * the GT's bring-up, execlists, the PPGTT and the power
             * management a host does, all host-tested; the process serves a
             * render-only chardev node and is started on ferrix.intelgpu.
             * The kernel lends it the screen by identity and maps its
             * buffers write-combining. On the box, M1 (the device answers)
             * and M2 (the first GPU commands) ran on 2026-10-20; M3, the
             * render node over the GT back end, is wired and not shown on
             * the box. */
    }

    // -----------------------------------------------------------------------
    // How the pieces fit
    // -----------------------------------------------------------------------

    #implemented part def DeviceStack {
        @stage { number = 10; }
        doc /* The drivers package as one whole. In the kernel: the firmware
             * tables and MMIO, the enumeration that turns them into device
             * nodes, and the IOMMU domains each node's DMA goes through. In
             * user space: devmgr, which gets a handle per node and starts one
             * driver process per matched node, and drvupdated, which brings
             * it new driver images. Each driver talks to the kernel subsystem
             * it serves over its channel and, for block and net, a shared
             * ring. */
        part acpi : AcpiAccess[0..1];
        part fdt : FdtAccess[0..1];
        part mmio : MmioWindows;
        part enumeration : DeviceEnumeration;
        part iommu : IommuDomains;
        part devmgr : DevMgr;
        part drvupdated : DrvUpdated[0..1];
        part drivers : DriverProcess[0..*];
    }

    #implemented action def DriverBootstrap {
        @stage { number = 10; }
        doc /* The loader places an initramfs in RAM holding devmgr, the
             * drivers and init. The kernel unpacks it into a tmpfs root and
             * starts devmgr from stage 10's boot check, and devmgr starts the
             * drivers; on a boot with a btrfs root disk the kernel then
             * mounts it and moves every process after onto it, as Linux's
             * switch_root does (src/kernel/extensions/personality/linux/src/fs/root_disk.rs), and starts init
             * last, after the boot marker. Linux's answer, for the same
             * reason. The test boots keep the tmpfs root, so only cargo
             * xtask run mounts a root disk and moves onto it. pivot_root
             * itself, so the tmpfs can be unmounted from under the new root,
             * is an init's work, which stage 15 owes. */
        first start;
        then action mountInitramfsAsRoot;
        then action startDevMgr;
        then action spawnBlockDriver;
        then action mountBtrfs;
        then action pivotRoot;
        then action startInit;
        then done;
    }
}
