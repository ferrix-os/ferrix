/*
 * Ferrix — SysML v2 model, part 13: the certified item's requirements.
 *
 * The high-level requirements of the certified item (the `core` and `item`
 * rings of docs/certification/ITEM.md): what each subsystem promises at its
 * interface, decomposed from the Security Target's objectives
 * (docs/certification/SECURITY-TARGET.md §4.1 and §8.2) and the safety
 * manual's assumed safety requirements (SAFETY-MANUAL.md §2). The low-level
 * requirements, one per unit of code, go in one file per subsystem after this
 * one. docs/certification/IMPLEMENTATION.md W-8 is the design, and
 * tools/common/check/check-traceability.py the gate that reads these and writes
 * docs/certification/TRACEABILITY.md.
 */
package FerrixItemRequirements {
    private import ScalarValues::*;
    private import FerrixStructure::Kernel;

    requirement def ItemRequirement {
        doc /* A requirement of the certified item. Unlike the goal and the
             * design rules of part 1, which say why the system is shaped as it
             * is, each of these says what the item shall do in terms a test
             * can pass or fail, and names the requirement above it that it
             * serves. The gate refuses one without all three. */
        subject item : Kernel;
        attribute statement : String {
            doc /* One sentence with "shall", about behaviour a program, a
                 * device or the boot log can observe. */
        }
        attribute criterion : String {
            doc /* The pass/fail condition a check tests, counted where there
                 * is something to count. */
        }
        attribute scope : String[0..1] {
            doc /* The flags this holds under, BUILD-FLAGS rule 7: `personality=kernel` for
                 * what a `personality=user` kernel does not build (M6.md, M.4). None: every
                 * configuration. Scoped is not withdrawn: withdrawn is for what is deleted. */
        }
        attribute parent : String[1..*] {
            doc /* The ids of the level above: for a high-level requirement a
                 * Security Target objective (O.*), an assumed safety
                 * requirement (ASR-*) or a goal requirement (G.*); for a
                 * low-level one, a high-level requirement (H.*). */
        }
    }

    requirement def ItemHighLevel :> ItemRequirement {
        doc /* What one subsystem of the item promises at its interface, with
             * an id `H.<AREA>.<n>`. The areas follow the families of
             * functional requirement the item implements. */
    }

    requirement def ItemLowLevel :> ItemRequirement {
        doc /* What one unit of the item's code does, with an id
             * `L.<module>.<n>`, and the unit named so that a renamed function
             * breaks the trace loudly. */
        attribute unit : String[1..*] {
            doc /* `path::function` or `path::Type::method`, relative to
                 * src/kernel/src: `mm::zero_frame`; or, for a library crate
                 * of the item, the same from the crate's src/ led by the
                 * crate's name: `ferrix_btrfs::volume::Volume::read_node`. */
        }
    }

    // -----------------------------------------------------------------------
    // The high level, one package per area. The areas follow the families of
    // SECURITY-TARGET.md §8.2 the item implements, and the safety manual's
    // ASR-1 to ASR-8; a requirement names every objective it serves.
    // -----------------------------------------------------------------------

    package Memory {
        doc /* Address spaces, the frames under them and the mappings that
             * reach them: O.ISOLATE, O.WXN and O.SCRUB, ASR-1, ASR-2 and
             * ASR-5 (FDP_IFC.1, FDP_IFF.1, FDP_RIP.2). */

        requirement <'H.MEM.1'> spacesAreSeparate : ItemHighLevel {
            attribute :>> statement = "A user address space shall translate a user
                virtual address only to a frame its own mappings name, so that one
                address in two address spaces reaches two frames unless a VMO both
                map shares one.";
            attribute :>> criterion = "Of N reads of one user address, made
                alternately in two address spaces that each wrote a different value
                there, all N return the reading space's own value and none the
                other's (the boot's `spaces` line, N = 128).";
            attribute :>> parent = ("O.ISOLATE", "ASR-1");
        }
        requirement <'H.MEM.2'> kernelMemoryIsNotUsers : ItemHighLevel {
            attribute :>> statement = "No mapping of kernel memory shall be
                accessible from user mode: a user-mode read, write or instruction
                fetch at a kernel address shall end in a fault delivered to the
                thread, never in the access.";
            attribute :>> criterion = "A program that reads, writes and jumps to a
                kernel-half address is ended with SIGSEGV each time, 3 of 3, on every
                architecture, and the kernel's memory at that address is unchanged.";
            attribute :>> parent = ("O.ISOLATE", "ASR-1");
        }
        requirement <'H.MEM.3'> kernelKeptOutOfUserPages : ItemHighLevel {
            attribute :>> statement = "On every processor the kernel shall run with
                its own access to user pages refused outside the window a user copy
                opens: SMEP and SMAP on x86-64, PAN on AArch64 where the processor
                implements it. ARMv7-A has no such control (AoU-6).";
            attribute :>> criterion = "The boot reports SMEP on and SMAP on (x86-64),
                or PAN on where offered (AArch64), for each of the N online
                processors; a kernel read of a user page outside the window faults.";
            attribute :>> parent = ("O.ISOLATE", "ASR-1");
        }
        requirement <'H.MEM.4'> writableOrExecutable : ItemHighLevel {
            attribute :>> statement = "Once bring-up has dropped the loader's
                identity map, no leaf mapping under the kernel's own root table or
                the identity root shall be both writable and executable.";
            attribute :>> criterion = "The boot's sweep of every leaf mapping under
                the kernel's root and the identity root counts N mappings, E > 0 of
                them executable, and 0 both writable and executable (the `w^x`
                line).";
            attribute :>> parent = ("O.WXN", "ASR-2");
        }
        requirement <'H.MEM.5'> imageIsSealed : ItemHighLevel {
            attribute :>> statement = "No mapping of the frames that hold the
                kernel's text and read-only data, the direct map's alias of them
                included, shall be writable.";
            attribute :>> criterion = "The boot's sweep of every mapping of those
                frames finds 0 writable, and finds the direct map aliasing every byte
                of them (the `sealed` line).";
            attribute :>> parent = ("O.WXN", "ASR-2");
        }
        requirement <'H.MEM.6'> framesZeroedBeforeUse : ItemHighLevel {
            attribute :>> statement = "A physical frame shall hold only zeros when it
                is committed to a VMO, mapped into a user address space for the first
                time, or made a page table.";
            attribute :>> criterion = "A frame written with a pattern, freed and
                committed again reads 0 non-zero bytes of its 4096 before the new
                owner's first write, for a VMO page and for a page table alike.";
            attribute :>> parent = ("O.SCRUB", "ASR-5");
        }
        requirement <'H.MEM.7'> nothingFreedBeforeItsShootdown : ItemHighLevel {
            attribute :>> statement = "A page-table frame an unmap empties shall not
                return to the frame allocator until the TLB invalidation that covers
                the unmap has been made.";
            attribute :>> criterion = "A page table an unmap empties is still held,
                not freed, until the shootdown covering it completes: 0 tables freed
                before it, and exactly the tables it emptied given back by it.";
            attribute :>> parent = ("O.ISOLATE", "ASR-1");
        }
        requirement <'H.MEM.8'> privateCopiesStayPrivate : ItemHighLevel {
            attribute :>> statement = "After a fork or a clone by handle, a write by the parent or the
                child to a private page shall not be visible to the other.";
            attribute :>> criterion = "The `cow` program, in which each side writes a
                page both shared, exits 61 (neither saw the other's write). On Bare, present and desktop (bare_side_check): as L.user.61.";
            attribute :>> parent = ("O.ISOLATE", "ASR-1");
        }
        requirement <'H.MEM.9'> framesComeBack : ItemHighLevel {
            attribute :>> statement = "Every frame an address space, a VMO or a
                process holds shall return to the frame allocator when the last
                reference to it goes.";
            attribute :>> criterion = "After each memory and program check, the free
                frame count is what it was before: 0 frames leaked, per check (the
                `objects`, `uaccess` and `exits` lines).";
            attribute :>> parent = "O.QUOTA";
        }
        requirement <'H.MEM.10'> imageRangeRefused : ItemHighLevel {
            attribute :>> statement = "Every interface that maps a physical range a
                caller names shall refuse a range that touches the kernel image.";
            attribute :>> criterion = "Requests naming the image's first page, its
                last page and a range straddling its end are each refused, 0
                accepted, at stages 1, 2 and 6.";
            attribute :>> parent = ("O.ISOLATE", "O.WXN");
        }
        requirement <'H.MEM.11'> allocationFailureIsAnswered : ItemHighLevel {
            attribute :>> statement = "An allocation the item makes after bring-up
                shall report failure to its caller, which shall answer it as running
                out of memory and keep nothing half made.";
            attribute :>> criterion = "With every allocation of the swept memory
                operations and native calls failed in turn, each failure is absorbed
                or answered NO_MEMORY or ENOMEM, and 0 frames or objects are left
                behind (the `sweep` and `no-mem` lines).";
            attribute :>> parent = "O.QUOTA";
        }
        // Split out of H.MEM.7 and H.MEM.5 by W-8 step 4 (mm and user), so that
        // one check proves each.
        // Note (ledger 8583, finding F-108): on x86-64 a large heap block's free
        // (L.mm.143) returns while another processor may still translate the freed
        // address until the area's purge; the address and its frame are nobody's
        // meanwhile. The statement stands unchanged; narrowing it is the customer's.
        requirement <'H.MEM.12'> remapsAreSeenEverywhere : ItemHighLevel {
            attribute :>> statement = "Once a change to a kernel mapping returns,
                every online processor shall translate the address as changed, and
                none through the translation it replaced.";
            attribute :>> criterion = "Of N moves of one page to another frame, each
                made after every online processor has read the page, every
                processor reads the moved page's new value each time: 0 stale reads
                (the `tlb` line).";
            attribute :>> parent = ("O.ISOLATE", "ASR-1");
        }
        requirement <'H.MEM.13'> theTextCannotBeWritten : ItemHighLevel {
            attribute :>> statement = "A write to the kernel's text through its
                direct-map alias shall fault, on every architecture.";
            attribute :>> criterion = "A kernel write to the first word of the text
                through the direct map ends in the page-fault report (FX-9001) on
                x86-64, AArch64 and ARMv7-A, 3 of 3, and the word is unchanged.";
            attribute :>> parent = ("O.WXN", "ASR-2");
        }
        // Added by W-8 step 4 (mm and user): behaviour of the kernel's own memory
        // and of user mappings that no requirement above said, and the halves of
        // H.MEM.7 and H.MEM.8 that one check each proves.
        requirement <'H.MEM.14'> kernelAllocationsHaveOneOwner : ItemHighLevel {
            attribute :>> statement = "The kernel's own frame allocator, heap and
                address arena shall hand each frame, block and range to one holder
                at a time, and shall never hand out frame 0.";
            attribute :>> criterion = "Stage 2's memory check finds two frames
                distinct, a 16-frame block 16-frame aligned, frame 0 neither managed
                nor handed out, a Box, a 4096-entry Vec and a 2048-key BTreeMap each
                holding what was put in it, and two arena ranges distinct, inside
                the arena and two guard pages apart.";
            attribute :>> parent = ("O.ISOLATE", "ASR-1");
        }
        requirement <'H.MEM.15'> kernelMappingsAreWhatWasAsked : ItemHighLevel {
            attribute :>> statement = "A mapping the kernel makes in its own address
                space shall translate each page to the frame or register asked for,
                with the permissions and memory type asked for.";
            attribute :>> criterion = "Each page of an 8-page arena range translates
                to a frame, none to its neighbour's; a page protected read-only reads back not
                writable in the descriptors and still translates; a device window at
                offset 0x40 translates to the register asked for, offset included,
                as device memory and not executable, and is gone once unmapped.";
            attribute :>> parent = ("O.ISOLATE", "ASR-1");
        }
        requirement <'H.MEM.16'> sharedWritesAreSeen : ItemHighLevel {
            attribute :>> statement = "After a fork or a clone by handle, a write by the child to a
                MAP_SHARED mapping shall be visible to the parent, and its write to a
                MAP_PRIVATE mapping shall not.";
            attribute :>> criterion = "The `shared` program exits 62 (its MAP_SHARED
                write reached the parent and its MAP_PRIVATE write did not). On Bare, present and desktop (bare_side_check): as L.user.62.";
            attribute :>> parent = ("O.ISOLATE", "ASR-1");
        }
        requirement <'H.MEM.17'> framesWaitForTheirInvalidation : ItemHighLevel {
            attribute :>> statement = "A frame taken out of a translation, of a user
                address space or of the kernel's, shall not return to the frame
                allocator until the TLB invalidation that covers it has been made on
                every processor that may still use the translation.";
            attribute :>> criterion = "A frame an unmap, a decommit or a replace
                takes out of a translation that another processor has cached is
                still allocated until that processor's shootdown returns: 0 frames
                freed before it, on every architecture.";
            attribute :>> parent = ("O.ISOLATE", "ASR-1");
        }
        requirement <'H.MEM.18'> userMappingsKeepTheirPermissions : ItemHighLevel {
            attribute :>> statement = "The kernel shall refuse to map a device
                window executable into a user address space, and a native VMO
                executable except through space_map with EXECUTE on both the space
                handle and the VMO handle (H.MEM.24), and shall map the vDSO's data
                page read-only.";
            attribute :>> criterion = "An executable device window and an executable
                vmo_map are each refused, 0 mapped; the vDSO's data page reads back
                not writable, and a write to it faults.";
            attribute :>> parent = ("O.WXN", "O.ISOLATE");
        }
        // Added by W-8 step 4 (smp): what a grace period promises, which no
        // requirement above said.
        requirement <'H.MEM.19'> gracePeriodsOutlastReaders : ItemHighLevel {
            attribute :>> statement = "Once a grace period the kernel waits for has
                ended, no read-side section that was running on any processor when
                the wait began shall still be running.";
            attribute :>> criterion = "A writer that replaces an object every other
                online processor is reading, waits a grace period and poisons the
                replaced one, 100 times over, leaves 0 reads of a poisoned object
                among more than 0 reads (the `grace` line).";
            attribute :>> parent = ("O.ISOLATE", "ASR-1");
        }
        // K2 of docs/MICROKERNEL.md section 3 (docs/microkernel/K2.md; the
        // consultant's OK IF, ledger 2845 and 2857).
        requirement <'H.OBJ.28'> aPagerSurvivesItsServer : ItemHighLevel {
            attribute :>> statement = "A pager with a keeper whose handle closes shall hold its
                outstanding requests until pager_take_up, which shall send each again to the new
                port under its own id, or the keeper's close, or each waiter's bound, whichever
                comes first; present pages and their Dirty state shall stay; and everything held
                meanwhile shall stay charged to the job that was charged for it.";
            attribute :>> criterion = "Stage 9's `rebind` line: read, dirty and copy waits across a
                close answered by the next instance, two cycles, each waiter's bound and the
                keeper's close ending parked waits.";
            attribute :>> parent = ("O.ISOLATE");
        }

        requirement <'H.OBJ.27'> aProcessRunsWhatItsCreatorMapped : ItemHighLevel {
            attribute :>> statement = "A native process made by process_make shall begin with an
                empty address space, and shall run only what its creator mapped, entered at an
                entry point and on a stack the kernel has checked lie in user space. In a kernel
                built with personality=user the kernel shall parse no image on any call a program
                can make.";
            attribute :>> criterion = "Stage 9's `build` line; in a personality=user build, the
                numbers of process_create and process_start answer ENOSYS.";
            attribute :>> parent = ("O.VALIDATE", "O.ISOLATE");
        }

        requirement <'H.MEM.26'> theFirstImagesComeFromTheInitramfs : ItemHighLevel {
            attribute :>> statement = "In a kernel built with personality=user, the kernel's one
                loader shall load only images read from the initramfs, for the processes the
                kernel itself starts, and constants of the in-kernel checks.";
            attribute :>> criterion = "check-item-boundary.py's loader rule: first_image::load is
                called only from discovery/devmgr.rs and check files, with a planted caller
                failing it. In present and desktop ferrix.devmgr=init still parses what pid 1
                left at /sbin/devmgr, as ITEM.md section 5 and VULNERABILITY-ANALYSIS.md say.";
            attribute :>> parent = ("O.VALIDATE");
        }

        requirement <'H.MEM.27'> theKernelsLoaderKeepsWXorX : ItemHighLevel {
            attribute :>> statement = "On every profile, the kernel's one loader shall leave no
                page both writable and executable, and shall refuse a malformed image and never
                panic; what a refused devmgr then does is stage 10's stated fatal.";
            attribute :>> criterion = "Stage 9's `build` line: 0 leaves writable and executable,
                7 malformed images refused.";
            attribute :>> parent = ("O.WXN", "ASR-2");
        }

        requirement <'H.MEM.28'> aMappedWriteStaysInTheDirtySet : ItemHighLevel {
            attribute :>> statement = "A write through a shared mapping of a disk file shall keep
                its page in the set fsync writes until a write-back that began after the write has
                ended; a page in that set shall not be reclaimed, and a page not written shall not
                be reported.";
            attribute :>> criterion = "Stage 6's `dirty` line and test-powerfail's mapped round.";
            attribute :>> parent = ("O.ISOLATE");
        }

        requirement <'H.MEM.24'> aSpaceByHandleIsHeldToItsRights : ItemHighLevel {
            attribute :>> statement = "An address space reached by handle shall be
                mapped, unmapped, protected and read only as that handle's rights
                allow; no mapping made by handle shall be both writable and
                executable; an executable mapping by handle shall need EXECUTE on
                the space handle and on the VMO handle; and a process's space shall
                be given by handle only to its creator, before it starts.";
            attribute :>> criterion = "Stage 9's `space` line: every by-handle call
                refused without its right, an executable mapping refused without
                EXECUTE on either handle and made with both, a writable and
                executable protection refused by the decoder and by the space
                itself, process_space refused without MANAGE, for a process its
                handle cannot reach and after the start, and the sweep of every
                user root the check reached finding 0 leaves writable and
                executable and more than 0 executable.";
            attribute :>> parent = ("O.ISOLATE", "O.WXN", "O.CAPABILITY", "ASR-2", "ASR-3");
        }
        requirement <'H.MEM.25'> aCloneNeverSeesItsSourcesLaterWrites : ItemHighLevel {
            attribute :>> statement = "A copy-on-write clone of an address space made
                by handle shall never see a write its source makes after the clone,
                by any path, nor the source one the clone makes; memory both map
                shared shall stay shared.";
            attribute :>> criterion = "Stage 9's `space` line, clone: the source's
                writable translation of a private page gone and a shootdown begun
                before space_clone answers; a write after the clone by either side,
                by a kernel copy and to a page made read-only before the clone and
                writable after it (F-41), unseen by the other; a shared mapping's
                write seen by both; a page both hold given back to one as the clone
                goes. A program's own store through a stale translation after a
                fork is stage 6's USER_COW_PROGRAM check (H.MEM.8, L.user.61;
                F-41 itself is L.user.60), through the same AddressSpace::fork.";
            attribute :>> parent = ("O.ISOLATE", "ASR-1");
        }
        // K3, pager-backed VMOs (docs/microkernel/K3.md; the consultant's OK
        // IF, ledger 2858).
        requirement <'H.MEM.29'> aSealedImageNeverChanges : ItemHighLevel {
            attribute :>> statement = "A sealed VMO's contents and length shall never
                change after its seal, and its digest shall be the kernel's, computed
                from its frames after the freeze.";
            attribute :>> criterion = "object::sealing_check on every boot, and
                check-vmo-seal-tags.py in xtask check; L.mm.111-114.";
            attribute :>> parent = ("O.CAPABILITY", "ASR-3");
        }
        requirement <'H.MEM.30'> aMeasuredSpaceRunsOnlyWhatIsMeasured : ItemHighLevel {
            attribute :>> statement = "A measured space's executable memory shall come
                only from sealed, measured VMOs and the kernel's own code pages, and
                its digests shall be recorded and never removed.";
            attribute :>> criterion = "object::sealing_check on every boot;
                L.mm.115-122, 124-126.";
            attribute :>> parent = ("O.CAPABILITY", "ASR-2");
        }
        requirement <'H.MEM.22'> aPagerAnswersWithinItsBound : ItemHighLevel {
            attribute :>> statement = "An absent page of a pager-backed VMO shall
                become present only by its pager's supply. A thread shall wait on a
                pager only for a fault on, or a kernel copy into, a pager-backed VMO
                its own process maps or names, and the wait shall end on the supply,
                the pager's failure, the process's end, the pager's close, or the
                pager's bound of at most 30 s; every ending but the supply shall
                give the faulting process SIGBUS or its call an error, and none
                shall stop the kernel.";
            attribute :>> criterion = "Stage 9's pager check (the `pager` line):
                faults forwarded and supplied, shared within a job and apart across
                jobs; failed, timed-out, closed and killed waits ended without their
                page, the bound held from below, the failures audited; copies
                waiting or refused; each with its negative control (K3.md section
                6).";
            attribute :>> parent = ("O.FAILSAFE", "O.ISOLATE");
        }
        requirement <'H.MEM.23'> noWriteLeavesTheDirtySet : ItemHighLevel {
            attribute :>> statement = "A write to a page of a pager-backed VMO
                shall keep the page in the dirty set until a write-back that began
                after the write ends; a page in the dirty set shall never be
                decommitted or reclaimed.";
            attribute :>> criterion = "Stage 9's pager check (the `pager` line): a
                Clean page is never mapped writable, a write-back takes the write
                right away before it returns, a write after it is Dirty after its
                end, and a decommit takes Clean pages only; each with its negative
                control (K3.md section 6).";
            attribute :>> parent = ("O.ISOLATE", "ASR-1");
        }
    }

    package Objects {
        doc /* Handles, rights and the objects they name: O.CAPABILITY and
             * ASR-3 (FDP_ACC.1, FDP_ACF.1, FMT_MSA.1, FMT_MSA.3). */

        requirement <'H.OBJ.1'> onlyThroughAHandle : ItemHighLevel {
            attribute :>> statement = "A native call shall act on an object only
                through a handle in the calling process's own handle table, and shall
                refuse a value naming no live handle there with BAD_HANDLE.";
            attribute :>> criterion = "Every native call given a value never issued,
                a value from another process's table and a value closed earlier is
                refused BAD_HANDLE: 0 of them act on an object.";
            attribute :>> parent = ("O.CAPABILITY", "ASR-3");
        }
        requirement <'H.OBJ.2'> rightsAreChecked : ItemHighLevel {
            attribute :>> statement = "A native call shall be refused with
                WRONG_TYPE when its handle names an object of another type, and with
                ACCESS_DENIED unless its handle carries every right the operation
                requires.";
            attribute :>> criterion = "For each native operation that requires a
                right, a call through a handle lacking it is refused ACCESS_DENIED,
                and a call through a handle of the wrong type WRONG_TYPE; 0 are
                performed.";
            attribute :>> parent = ("O.CAPABILITY", "ASR-3");
        }
        requirement <'H.OBJ.3'> duplicatesNeverRaise : ItemHighLevel {
            attribute :>> statement = "Duplicating a handle shall need the DUPLICATE
                right and yield rights that are a subset of the source's; asking for
                a right the source lacks shall be refused with ACCESS_DENIED.";
            attribute :>> criterion = "A duplicate of a handle without DUPLICATE is
                refused ACCESS_DENIED; one asking for a right the source lacks is
                refused ACCESS_DENIED and the source keeps its rights; a narrower
                copy is made with the rights asked for.";
            attribute :>> parent = ("O.CAPABILITY", "ASR-3");
        }
        requirement <'H.OBJ.4'> staleValuesRefused : ItemHighLevel {
            attribute :>> statement = "A handle value shall stop naming its object
                when the handle is closed or transferred, and shall not name the
                object its slot holds next.";
            attribute :>> criterion = "A value whose handle was closed is refused
                BAD_HANDLE, on a get and on a second close, after its slot is
                reused, and the reused slot issues a new value.";
            attribute :>> parent = ("O.CAPABILITY", "ASR-3");
        }
        requirement <'H.OBJ.5'> handlesMoveOnlyInMessages : ItemHighLevel {
            attribute :>> statement = "A handle shall pass from one process to another
                only inside a channel message, leaving the sender's table in the same
                step, and a write that is refused shall leave every handle it carried
                with the sender.";
            attribute :>> criterion = "After a write carrying handles each is refused
                BAD_HANDLE in the sender and works in the reader; writes refused
                PEER_CLOSED, TOO_BIG and SHOULD_WAIT leave every carried handle
                usable by the sender; a handle without TRANSFER is refused
                ACCESS_DENIED.";
            attribute :>> parent = ("O.CAPABILITY", "ASR-3");
        }
        requirement <'H.OBJ.6'> newProcessHoldsNothing : ItemHighLevel {
            attribute :>> statement = "A process shall start holding no handle but
                the bootstrap handle its creator explicitly passes, and a fork shall
                not copy the native handle table.";
            attribute :>> criterion = "A created process holds 0 handles before it
                starts and exactly 1 after a start that passed a bootstrap; a forked
                child's native handle table is empty.";
            attribute :>> parent = ("O.CAPABILITY", "ASR-3");
        }
        requirement <'H.OBJ.7'> tableIsBounded : ItemHighLevel {
            attribute :>> statement = "A process's handle table shall hold at most
                4096 handles, refuse an insertion past that with NO_HANDLES, and lose
                nothing it could not deliver.";
            attribute :>> criterion = "Duplicating until refused ends in NO_HANDLES
                with at most 4096 held; a channel read and a VMO create into the full
                table are refused NO_HANDLES and the message stays queued (the
                `refusals` line).";
            attribute :>> parent = ("O.CAPABILITY", "O.QUOTA");
        }
        requirement <'H.OBJ.8'> objectsEndWithTheirLastHandle : ItemHighLevel {
            attribute :>> statement = "An object shall be destroyed when the last
                handle to it closes.";
            attribute :>> criterion = "One object of each kind, made and its last
                handle closed, is destroyed by the time the close returns or the
                drain after it ends: 0 of them outlive it, and 0 frames are
                leaked.";
            attribute :>> parent = ("O.CAPABILITY", "O.QUOTA");
        }
        requirement <'H.OBJ.9'> killingAJobEndsItsTree : ItemHighLevel {
            attribute :>> statement = "Killing a job shall end every process in it
                and in every job beneath it.";
            attribute :>> criterion = "4 processes in a tree of three jobs are all
                ended by two kills, and each wait on them is woken (the `jobs`
                line).";
            attribute :>> parent = ("O.CAPABILITY", "O.QUOTA");
        }

        // H.OBJ.10 to H.OBJ.17 were added by the low-level pilot on object/
        // (IMPLEMENTATION.md W-8, step 3). H.OBJ.10, 12 and 13 are behaviour
        // object/ implements that no requirement said; H.OBJ.14 to 17 are the
        // halves split out of H.OBJ.3, 4, 8 and 11, so that one check can prove
        // each whole, since a `Verifies:` tag credits the whole requirement.
        // H.OBJ.8 itself is now one check of every kind of object, which does
        // not exist yet; its low-level requirements prove it kind by kind.

        requirement <'H.OBJ.10'> queuesAreBounded : ItemHighLevel {
            attribute :>> statement = "Every queue a program can fill in the kernel
                shall be bounded -- a channel end's unread messages at 256, a port's
                user packets at 1024, an object's port registrations at 64 -- and an
                addition past the bound shall be refused without being queued.";
            attribute :>> criterion = "Writing to a channel nobody reads is refused
                SHOULD_WAIT at its bound, and queueing on a port nobody takes from is
                refused SHOULD_WAIT at exactly 1024 packets, 0 queued past either
                bound, and draining the channel makes room again; the 65th
                registration on one object is refused.";
            attribute :>> parent = "O.QUOTA";
        }
        requirement <'H.OBJ.11'> waitsEndAtTheirSignal : ItemHighLevel {
            attribute :>> statement = "A wait on an object shall end when a signal
                it waits for is asserted, at once if one already is, and shall not
                end before its deadline while none is.";
            attribute :>> criterion = "A wait on an empty channel end with a zero
                deadline times out; one with a two-minute deadline is ended by a
                message written 20 ms later, not before it, and reports READABLE; a
                wait for PEER_CLOSED on an end whose peer has closed returns at
                once.";
            attribute :>> parent = ("G.7", "O.CAPABILITY");
        }
        requirement <'H.OBJ.12'> jobsAreCgroups : ItemHighLevel {
            attribute :>> statement = "The job tree shall be the cgroup v2
                hierarchy: every process in exactly one job, a job populated exactly
                while it or a job beneath it has a member not yet released, and a
                job refusing a process or a child that its killed or removed state,
                its limits or the no-internal-process rule forbid.";
            attribute :>> criterion = "A new process is in the root job and a fork's
                child in its parent's; a job empties at its last member's release
                and wakes its waiters; a move a job refuses leaves the process where
                it was; a removed job takes neither a process nor a child; a child
                past cgroup.max.depth or cgroup.max.descendants is refused.";
            attribute :>> parent = ("G.8", "O.QUOTA");
        }
        requirement <'H.OBJ.13'> pidsNameOneProcess : ItemHighLevel {
            attribute :>> statement = "A pid shall name at most one process at a
                time, and a pid given back shall not be handed out again before
                allocation has come round the whole range past it.";
            attribute :>> criterion = "Allocating through the whole range wraps to
                300 and passes over a pid still held: 0 pids handed out twice and
                none below 300 after the wrap.";
            attribute :>> parent = ("G.4", "O.ISOLATE");
        }
        requirement <'H.OBJ.14'> replacesNeverRaise : ItemHighLevel {
            attribute :>> statement = "Replacing a handle shall close the source and
                yield rights that are a subset of its; asking for a right the source
                lacks shall be refused with ACCESS_DENIED and leave the source as it
                was.";
            attribute :>> criterion = "A replace asking for a right not held is
                refused ACCESS_DENIED and the source keeps its rights; a narrower
                replace closes the source and leaves one handle, with the rights
                asked for.";
            attribute :>> parent = ("O.CAPABILITY", "ASR-3");
        }
        requirement <'H.OBJ.15'> usedUpSlotsRetire : ItemHighLevel {
            attribute :>> statement = "A slot whose generations are all used shall
                be retired, so that no handle value is ever issued twice.";
            attribute :>> criterion = "After every generation of one slot has been
                issued and closed, the next handle comes from another slot, and 0 of
                the values issued before it are issued again or resolve.";
            attribute :>> parent = ("O.CAPABILITY", "ASR-3");
        }
        requirement <'H.OBJ.16'> thePeerSeesTheClose : ItemHighLevel {
            attribute :>> statement = "The peer of a destroyed channel end shall
                observe PEER_CLOSED from the moment the close returns, and what the
                destroyed end held shall be freed.";
            attribute :>> criterion = "After one end of a channel holding a queued
                VMO is closed, a read and a write on the survivor are refused
                PEER_CLOSED, 2 of 2, and 0 frames are leaked.";
            attribute :>> parent = ("O.CAPABILITY", "O.QUOTA");
        }
        requirement <'H.OBJ.17'> registrationsFireOnce : ItemHighLevel {
            attribute :>> statement = "A port registration shall queue exactly one
                packet, with its key and the asserted signals it asked for, when one
                of them is first asserted, at once if one already is.";
            attribute :>> criterion = "A registration does not fire before its
                signal, fires once on the message that asserts it and not on a
                second, fires at once for a state already true, and fires when the
                peer closes for PEER_CLOSED, each packet with its key.";
            attribute :>> parent = ("G.7", "O.CAPABILITY");
        }
        requirement <'H.OBJ.18'> theFastPathIsTheGeneralPath : ItemHighLevel {
            attribute :>> statement = "Every result of channel_write_read answered by
                the fast path shall be a result the general path gives in the same
                circumstances, and the fast path shall bypass no filter, audit record
                or speculation barrier. x86-64 only, in a kernel built with ipc_fastpath=on.";
            attribute :>> criterion = "ipc-equiv's transcripts with the fast path on
                and off are the same line for line, with trips taken on and no
                counter moved off (`cargo xtask test-ipc-equiv`); stage 9's fast path
                cases hold both boots to the general path's results (the `fastcase`
                line); a filtered call is refused with the filter's errno.";
            attribute :>> parent = ("G.7", "O.CAPABILITY");
        }
        requirement <'H.OBJ.22'> aSealedJobKeepsItsOwn : ItemHighLevel {
            attribute :>> statement = "A process in a sealed job shall leave that
                job's tree only by ending and shall start no process outside it;
                a job made inside a sealed job shall be sealed, and no job shall
                be unsealed.";
            attribute :>> criterion = "Stage 13's cgroupfs check: root's moves
                out of, within and into a sealed tree are refused EPERM and every
                process stays; a sealed member's starts outside its tree are
                refused; jobs made inside a sealed one read as sealed; and every
                job in drivers.slice reads as sealed (the sysfs check);
                test-restart --boot intel-keeper's root move of the GPU's worker
                out of its driver job is refused (INTEL-GPU.md §12.11 S1). And with kernel objects alone, on every profile, the `core obj` line (object/rehome_check.rs::check_a_seal_holds, object/rehome_check.rs::check_may_start_in, object/rehome_check.rs::check_sealed_tree).";
            attribute :>> parent = ("G.8", "O.QUOTA", "O.CAPABILITY");
        }
        requirement <'H.OBJ.19'> everyMessageSaysWhoWroteIt : ItemHighLevel {
            attribute :>> statement = "Every channel message shall carry the identity
                of the process that wrote it and of the job that process was in at the
                write, written by the kernel at the write and never taken from the
                message or the writer's arguments, and readable by its reader with the
                message; a process's identity shall never be given to another process
                while the kernel runs. A message the kernel writes shall carry zero
                and zero, which attest that the kernel wrote it, not that its content
                is the kernel's own. The identity is the writer's, not its
                credentials (docs/microkernel/K6.md, MICROKERNEL.md §3 K6).";
            attribute :>> criterion = "Stage 9's `sender` line: messages read with
                channel_read_attested carry their writer's process and job ids, which
                object_id confirms, whatever the body says, through the slot, either
                end's transfer, the writer's end and a move between jobs; the kernel's
                read as zero and zero; every process made has an id above every
                earlier one; channel_write_read answers none. Stage 8's exec check: a
                process's id survives its execve. Each with its negative control
                (K6.md §7).";
            attribute :>> parent = ("G.7", "O.CAPABILITY");
        }
        requirement <'H.OBJ.21'> timersFireInTheirWindowOnce : ItemHighLevel {
            doc /* docs/microkernel/K10.md, MICROKERNEL.md §3 K10. The lateness
                bound, and the interference between jobs' timers on one
                processor that makes it, is MEMORY-AND-TIMING.md §2.2ab's, owned
                by K9. */
            attribute :>> statement = "A timer object shall signal its waiters and
                the ports registered on it no earlier than its deadline and within
                its slack plus the lateness MEMORY-AND-TIMING.md §2.2ab states, at
                most once a set; never for an arm a later set or cancel superseded,
                nor after its last handle closed; and shall be charged to the job
                that made it, one object and its heap as kernel memory.";
            attribute :>> criterion = "Stage 9's `timers` line on every boot: a
                timer is heard no earlier than its deadline, a cancelled or
                superseded arm and a closed timer are never heard, and a timer is
                charged to its job and refused past its object limit
                (object::timer_check).";
            attribute :>> parent = ("G.7", "O.CAPABILITY", "O.QUOTA");
        }
        requirement <'H.OBJ.20'> aWaitOnAWordSleepsOnlyWhileItHolds : ItemHighLevel {
            doc /* K5, docs/microkernel/K5.md; the consultant's condition (7):
                 * a wake can come from any process that can read the word, so
                 * a woken wait is allowed to find its word unchanged. */
            attribute :>> statement = "A wait on a word of user memory shall sleep
                only while the word holds the value its caller gave, shall end when
                a wake of its word takes it, when its deadline passes or when its
                caller must leave, and shall be charged to its caller's job; a wake
                shall end at most the number of waits it names. A woken wait may
                find its word unchanged.";
            attribute :>> criterion = "Stage 9's address-wait check: waits by
                mapping and by handle woken across processes, changed words
                refused, counts, bitsets, a requeue, a wait on many words, a
                deadline, an ended process and a job's limit (the `addrwait`
                line).";
            attribute :>> parent = ("G.7", "O.QUOTA");
        }
        requirement <'H.OBJ.23'> theModeNamesTheTable : ItemHighLevel {
            attribute :>> statement = "A shared process's calls shall reach its private handle table from
                restricted mode and its region's shared table from normal mode, by
                the mode alone and never by an argument.";
            attribute :>> criterion = "The `regions` line on every boot of x86-64: restricted-check holds
                every case; a number in one table means nothing in the other.";
            attribute :>> parent = ("O.CAPABILITY");
        }
        requirement <'H.OBJ.24'> aHandleCrossesOnlyByTheTwoMoves : ItemHighLevel {
            attribute :>> statement = "A handle shall cross between the shared and private tables only
                through HANDLE_TO_SHARED and HANDLE_TO_PRIVATE, its rights
                checked.";
            attribute :>> criterion = "The `regions` line on every boot of x86-64: restricted-check holds
                every case; the moves refused without TRANSFER, with wider rights,
                or naming nothing.";
            attribute :>> parent = ("O.CAPABILITY");
        }
        requirement <'H.OBJ.25'> aSharedProcessHasItsOwnRestrictedSpace : ItemHighLevel {
            attribute :>> statement = "PROCESS_CREATE_SHARED shall make a process with a restricted space
                of its own, and no reach into another's.";
            attribute :>> criterion = "The `regions` line on every boot of x86-64: restricted-check holds
                every case; a second process's copy of the first's restricted
                memory faults.";
            attribute :>> parent = ("O.ISOLATE");
        }
        requirement <'H.OBJ.26'> theRegionIsSeenInNormalModeOnly : ItemHighLevel {
            attribute :>> statement = "A region's mappings shall reach every process of its partition in
                normal mode and none in restricted mode.";
            attribute :>> criterion = "The `regions` line on every boot of x86-64: restricted-check holds
                every case; a word and a page of the region are seen by two
                processes, and a change reaches a thread on another processor.";
            attribute :>> parent = ("O.ISOLATE");
        }
        requirement <'H.OBJ.30'> aLiftedLinuxReachesWhatItIsGiven : ItemHighLevel {
            attribute :>> statement = "Under personality=user a partition's Linux layer shall run as a
                program, reaching the kernel's objects only through handles it was
                given and its calls only from normal mode.";
            attribute :>> criterion = "test-linuxd's `lift-calls` line; restricted-check's table of the
                calls; the controls of docs/microkernel/M5-LIFT.md §12.";
            attribute :>> parent = ("O.ISOLATE");
        }
        requirement <'H.OBJ.34'> aLowerLevelReachesNothingOfAHigher : ItemHighLevel {
            attribute :>> statement = "A job shall have a criticality level fixed as it is made, at most
                its parent's, and the kernel shall refuse, and audit, what would
                let a lower level hold a handle to a higher job's processes,
                threads, jobs, spaces, region or exceptions, write a VMO a higher
                level maps other than a declared buffer, or serve as its pager.";
            attribute :>> criterion = "The `levels` line on every boot.";
            attribute :>> parent = ("O.ISOLATE");
        }
    }

    package Scheduling {
        doc /* Processor time: the fair class, placement and sleep. ASR-8
             * (partially met: the item has no admission control for real-time
             * work, AoU-4, so none is required here) and O.QUOTA's share of a
             * processor (FRU_RSA.1's refinement). */

        requirement <'H.SCHED.1'> runnableTasksRun : ItemHighLevel {
            attribute :>> statement = "Every runnable task shall run: no task shall
                stay runnable without being scheduled while processors are online.";
            attribute :>> criterion = "1000 threads spawned across the online
                processors all run to completion within the check's deadline (the
                `tasks` line).";
            attribute :>> parent = ("G.1", "ASR-8");
        }
        requirement <'H.SCHED.2'> lagIsBounded : ItemHighLevel {
            attribute :>> statement = "Among processor-bound tasks of equal weight on
                one processor, no task's service shall lag its fair share by more
                than one scheduling slice plus the timer overruns served in the
                window.";
            attribute :>> criterion = "With 12 spinners on every processor, each
                processor's worst lag is at or below that bound (the `fair` line).";
            attribute :>> parent = ("ASR-8", "O.QUOTA");
        }
        requirement <'H.SCHED.3'> jobsShareByWeight : ItemHighLevel {
            attribute :>> statement = "Under contention a job shall receive processor
                time in proportion to its weight, whatever the number of tasks in
                it.";
            attribute :>> criterion = "One task alone in a job keeps half of a
                processor, within the check's stated tolerance, against eight tasks
                in a sibling job of equal weight (the `quota` line).";
            attribute :>> parent = ("O.QUOTA", "ASR-8");
        }
        requirement <'H.SCHED.4'> affinityIsObeyed : ItemHighLevel {
            attribute :>> statement = "A task shall run only on the processors its
                affinity mask allows.";
            attribute :>> criterion = "Spinners confined to processors 0 and 1, twice
                as many as there are online processors, are seen running on no other
                processor: 0 violations.";
            attribute :>> parent = "G.1";
        }
        requirement <'H.SCHED.5'> sleepIsNotCutShort : ItemHighLevel {
            attribute :>> statement = "A task that sleeps for a duration shall not be
                woken before the duration has passed, and shall be woken within
                twenty times it.";
            attribute :>> criterion = "A 20 ms sleep returns after at least 20 ms and
                at most 400 ms (the `sleep` line).";
            attribute :>> parent = ("G.1", "ASR-8");
        }
        // Added by W-8 step 4 (smp): the per-processor record everything that
        // runs on a processor finds itself by, which no requirement above said.
        requirement <'H.SCHED.6'> eachProcessorFindsItsOwnRecord : ItemHighLevel {
            attribute :>> statement = "Code running on a processor shall find,
                through that processor's per-processor register, the record that
                names that processor and no other.";
            attribute :>> criterion = "In 100 rounds of work run on every online
                processor at once, each processor runs each round once and the record
                its register gives it names its own hardware identifier every time: 0
                misplaced runs (the `smp` line).";
            attribute :>> parent = ("O.ISOLATE", "ASR-1");
        }
        requirement <'H.SCHED.7'> threadLocalDescriptorsPerThread : ItemHighLevel {
            attribute :>> statement = "A thread's thread-local segment descriptors
                and data selectors shall be its own whenever it runs in ring 3,
                never another thread's. x86-64 only.";
            attribute :>> criterion = "Two i386 programs pinned to one processor,
                with one descriptor slot and selector but bases 4 bytes apart, each
                read their own word through %gs 200 times across sched_yield: both
                exit 42.";
            attribute :>> parent = ("O.ISOLATE", "G.1");
        }
        requirement <'H.SCHED.8'> userRegisterStatePerTask : ItemHighLevel {
            attribute :>> statement = "The user-mode state a trap does not save --
                on x86-64 the FS and GS bases and the x87 and SSE registers; on
                ARMv7-A the thread ID registers TPIDRURO and TPIDRURW, the VFP
                registers and FPSCR, and user mode's banked sp and lr -- shall be
                the running task's own whenever it runs in user mode, inherited by
                a fork child and reset by an execve, except that the vector
                registers of a task resumed from a blocking native call may be the
                initial state instead (H.SCHED.12). Every VFP register and FPSCR a
                program can read in user mode shall be its own; on ARMv7-A, while
                FPEXC.EN is clear for a task that has not used VFP, its VFP state
                is the one its record holds, which its first VFP instruction
                loads.";
            attribute :>> criterion = "Two programs pinned to one processor, each
                with its own FS and GS bases and XMM, MXCSR and x87 control values
                on x86-64, or its own TPIDRURO and TPIDRURW on ARMv7-A, read back
                their own across N yields: 0 mismatches; a fork child reads its
                parent's, and an execve'd image the reset values (the ARMv7-A `tls`
                line); on ARMv7-A a program's first VFP instruction reads its own
                record, never another program's registers, after a handover, a
                signal frame, a fork and an execve (the `lazy` line).";
            attribute :>> parent = ("O.ISOLATE", "G.1");
        }
        requirement <'H.SCHED.9'> vdsoClocksAnswerAsTheCall : ItemHighLevel {
            attribute :>> statement = "A clock read through the vDSO shall answer as
                the system call would, between system calls made on either side of
                it.";
            attribute :>> criterion = "A program reading each of the 7 clocks,
                gettimeofday and time through the vDSO finds each answer between
                system calls made on either side: exit 120.";
            attribute :>> parent = "G.5";
        // H.SCHED.10 and H.SCHED.11 were added by W-8 step 4 (console): the
        // processor time console output may take, which no requirement said.
        requirement <'H.SCHED.10'> consoleHoldsAreBounded : ItemHighLevel {
            attribute :>> statement = "Console output shall hold a processor with
                interrupts masked only for bounded work: a writer shall put at most 64
                bytes into the port and queue at most 2,048 bytes of a task's write
                per hold of the port's lock, and the port's interrupt shall make at
                most 68 passes, each taking at most 8,192 received bytes and giving
                the port at most 64.";
            attribute :>> criterion = "Across a task's 16 KiB write on a port with an
                interrupt, 0 holds of the port's lock put more than 64 bytes into the
                port or queue more than 2,048; a port that never reports itself empty
                lets its interrupt handler return after 68 passes.";
            attribute :>> parent = "O.QUOTA";
        }
        requirement <'H.SCHED.11'> consoleWritersSleepForRoom : ItemHighLevel {
            attribute :>> statement = "A task writing to the console that may sleep
                shall sleep while the fixed 4,096-byte transmit ring has no room for
                its next chunk, and a writer that may not sleep shall never sleep on
                the console.";
            attribute :>> criterion = "A task writing 16 KiB faster than the port
                sends sleeps at least once while the ring never holds more than 4,096
                bytes, and every byte reaches the port in order; a program's write
                made with a spin lock held returns without sleeping and its line
                reaches the port.";
            attribute :>> parent = "O.QUOTA";
        }
        requirement <'H.SCHED.12'> blockedNativeCallVectorState : ItemHighLevel {
            attribute :>> statement = "A task resumed after blocking in
                channel_write_read, object_wait_one or port_wait shall hold in its
                vector registers either its own state or, on x86-64 (made with
                SYSCALL), every component's initial state with its own MXCSR and x87
                control word, and on ARMv7-A (made with svc), zero in d0-d7 and
                d16-d31 with its own d8-d15 and FPSCR; never a value another program
                left. Every other call, and AArch64, keeps the whole state
                (H.SCHED.8).";
            attribute :>> criterion = "A program blocked in one of the calls, every
                vector register its pattern, beside a second program filling them
                with another on its processor, reads back neither pattern where its
                registers are lost, and its own MXCSR and control word, or its own
                FPSCR and d8-d15, after a message, its peer's close and a message
                with a signal pending; blocked in a Linux call, preempted, or past
                the woken call, it reads its own (the `vectors` line on x86-64 and
                on ARMv7-A).";
            attribute :>> parent = ("O.ISOLATE", "G.1");
        }
        requirement <'H.SCHED.13'> theDirectSwitchIsThePick : ItemHighLevel {
            attribute :>> statement = "A switch channel_write_read's fast path makes
                without the run queue's pick shall leave every scheduling quantity as
                the pick would leave it, and shall be made only when the pick could
                choose nothing else: the task switched to asleep at home on this
                processor, nothing else waiting and no sleeper due.";
            attribute :>> criterion = "RunQueue::hand_over equals enqueue, the
                rescale, remove_curr and pick_next field for field on 200,000 random
                queues (the ferrix-sched host test); a spinner beside the trips keeps
                its share, and an echo pinned to another processor never runs on the
                caller's (the `fastcase` line).";
            attribute :>> parent = ("G.1", "ASR-8");
        }
        requirement <'H.SCHED.14'> processorTimeIsSplitAndSwitchesCounted : ItemHighLevel {
            attribute :>> statement = "A task's processor time shall be reported split
                into the time it spent in the kernel and the rest, and the switches
                away from it shall be counted as voluntary or involuntary.";
            attribute :>> criterion = "Programs spinning in user mode are charged
                under a quarter of their runtime as kernel time, programs making
                system calls or taking page faults over half; tasks yielding to each
                other count involuntary switches, a task that sleeps voluntary ones
                (the `vtime` lines).";
            attribute :>> parent = "G.1";
        }
        requirement <'H.SCHED.15'> aTaskNotRunningIsReportableFromOutside : ItemHighLevel {
            attribute :>> statement = "A task that is not running shall be reportable
                from outside it, from what its entry from user mode and its switch
                away already saved, without the report faulting, changing the task,
                or adding work to any path the task takes.";
            attribute :>> criterion = "A thread blocked in a system call reads back
                its call's number and arguments, a blocked kernel task's chain ends
                in the chain it recorded itself, and a freed stack and a device
                window read as nothing (docs/DEBUG.md section 1.3).";
            attribute :>> parent = "G.1";
        }
        requirement <'H.SCHED.16'> aWokenTaskRunsBesideAnotherJobsLoad : ItemHighLevel {
            attribute :>> statement = "A task of one job, woken while a ring-3 load of
                another job saturates every processor, shall be running within the
                phase's bound in tools/common/xtask/src/stall.rs for that load: what the load's
                requests make the kernel do on its behalf -- holding a lock, freeing
                what its tasks left -- shall not keep other jobs' tasks off every
                processor (finding F-95).";
            attribute :>> criterion = "cargo xtask test-stall: 10 ms sleepers, one
                pinned to each processor and one free, beside each load phase, within
                the phase's bound in tools/common/xtask/src/stall.rs in a run whose
                quiet phases are within theirs; until a phase is asserted there, it
                is reported, and docs/PREEMPTIBLE-WAITS.md section 7 says which.";
            attribute :>> parent = ("ASR-8", "O.QUOTA");
        }
        requirement <'H.SCHED.18'> anUnstableCoreLeavesServiceWhole : ItemHighLevel {
            doc /* docs/CORE-QUARANTINE.md (customer, 2026-10-30, item 6;
                consultant OK IF Q1-Q14, ledger 4856). */
            attribute :>> statement = "A processor taken out of service shall be
                left by every task and every movable interrupt, with no task
                stranded on it and none run there, no interrupt lost, none
                delivered there once its messages are moved -- between the
                park and the move it may still take one, and runs its handler
                -- no stale translation kept when it returns, and a park it
                never acknowledges undone by its deadline; only root, through
                cpuN/online, and lode, through the processor service token,
                may ask, each change audited.";
            attribute :>> criterion = "cargo xtask test-quarantine and
                test-quarantine-smp2 (KVM): lode takes the target out after
                eleven core-scoped corrected records; nothing runs or is
                drained there; a reader blocked on an empty pipe is re-homed
                at its wake; its interrupts are moved and none lands there
                under disk traffic; the surface says so; the refused writes
                are refused; root brings it back; fifty times out and back
                under load. Negative controls (ledger 4932): the ACTIVE bit
                never cleared, the re-home removed, the retarget skipped,
                the park loop with interrupts masked, the capability check in
                the writer's own namespace -- each fires.";
            attribute :>> parent = "ASR-8";
        }
        requirement <'H.SCHED.28'> aReservationHoldsItsProcessorsShare : ItemHighLevel {
            attribute :>> statement = "Under schedule=edf a thread with the authority may hold a
                budget in each period on one processor: a set too wide for it shall be refused
                by name, the thread shall run no more than its budget in a period, the earliest
                deadline with budget shall run first, and the fair class shall have the rest.";
            attribute :>> criterion = "L.sched.179 to L.sched.183. No timing claim.";
            attribute :>> parent = "ASR-8";
        }
    }

    package Interrupts {
        doc /* Interrupt lines given to ring-3 drivers as objects: O.CAPABILITY
             * and ASR-3 for who receives one, O.QUOTA for what an unacknowledged
             * or unclaimed line can cost. */

        requirement <'H.IRQ.1'> deliveredToTheHolder : ItemHighLevel {
            attribute :>> statement = "An interrupt on a line bound to an Interrupt
                object shall be delivered only to that object, waking the task
                waiting on it.";
            attribute :>> criterion = "16 of 16 deliveries end their wait by waking
                it (the `wake` line), and no other waiter is woken.";
            attribute :>> parent = ("O.CAPABILITY", "ASR-3");
        }
        requirement <'H.IRQ.2'> maskedUntilAcknowledged : ItemHighLevel {
            attribute :>> statement = "A line bound to an Interrupt object shall be
                delivered to its holder once until the holder acknowledges it; a
                line the interrupt controller holds shall stay masked from its
                delivery until the acknowledgement, and an edge-triggered MSI-X
                vector shall reach the kernel's handler at most 65 times between two
                acknowledgements before it is masked until the next; and the line
                shall be masked when the object is destroyed.";
            attribute :>> criterion = "A line held from delivery to acknowledgement
                is delivered once and 0 times more before the acknowledgement; an
                MSI-X vector delivered 65 times unacknowledged reads masked (the
                `irq` line); after the last handle to its object closes, the line is
                masked.";
            attribute :>> parent = ("O.CAPABILITY", "O.QUOTA");
        }
        requirement <'H.IRQ.3'> unclaimedLinesMasked : ItemHighLevel {
            attribute :>> statement = "An interrupt on a line no object and no kernel
                handler holds shall be masked and counted, and delivered to nobody.";
            attribute :>> criterion = "A delivery provoked on a line nobody holds
                leaves the line masked and the unclaimed count one higher, with 0
                deliveries (the `edges` line).";
            attribute :>> parent = "O.QUOTA";
        }
    }

    package DirectMemoryAccess {
        doc /* Devices driven from ring 3 through apertures and IOMMU domains:
             * O.DMA and ASR-4 (FDP_ACF.1, FDP_IFF.1). ARMv7-A's reference
             * board has no IOMMU, so these hold on x86-64 and AArch64 only
             * (AoU-6). H.DMA.6 and H.DMA.7 are split from H.DMA.2, and
             * H.DMA.8 from H.DMA.3, so that one check can prove each (W-8's
             * iommu slice). That a pin is made only through a device handle
             * the driver holds is H.OBJ.1 and H.OBJ.2's: vmo_pin is a native
             * call like any other. */

        requirement <'H.DMA.1'> everyFunctionBehindAUnit : ItemHighLevel {
            attribute :>> statement = "Where a translating IOMMU is present, every
                PCI function the kernel enumerates shall be placed behind a unit
                before its driver starts, and a function no unit covers shall be
                reported.";
            attribute :>> criterion = "The boot counts N functions behind units, 0
                bypassing and 0 unresolved (the `iommu` line), with VT-d on x86-64
                and SMMUv3 on AArch64.";
            attribute :>> parent = ("O.DMA", "ASR-4");
        }
        requirement <'H.DMA.2'> outOfDomainWritesRefused : ItemHighLevel {
            attribute :>> statement = "A device write to an address outside its
                domain shall be refused by the unit and recorded as a fault against
                the device's stream and the page it addressed.";
            attribute :>> criterion = "A device made to write a page its translated
                domain does not map has the write recorded by its unit as a write by
                its stream to that page: 1 or more out-of-domain writes faulted (the
                `pci` line) on x86-64 and AArch64.";
            attribute :>> parent = ("O.DMA", "ASR-4");
        }
        requirement <'H.DMA.6'> noFaultUnprovoked : ItemHighLevel {
            attribute :>> statement = "A boot shall end with no DMA fault recorded
                that no check provoked.";
            attribute :>> criterion = "Last before the success marker, the audit
                reads every translating unit's records and counts 0 faults no check
                provoked, unit events and overflows included (the `iommu` audit
                line).";
            attribute :>> parent = ("O.DMA", "ASR-4");
        }
        requirement <'H.DMA.7'> refusedWritesReachNothing : ItemHighLevel {
            attribute :>> statement = "A device write its unit refuses shall reach
                no memory.";
            attribute :>> criterion = "A device made to write a frame the kernel
                holds and its domain does not map leaves every byte of the frame as
                it was.";
            attribute :>> parent = ("O.DMA", "ASR-4");
        }
        requirement <'H.DMA.3'> onlyPinnedFramesReachable : ItemHighLevel {
            attribute :>> statement = "A device's domain shall translate a frame's
                address only while the frame is pinned into it, and shall refuse a
                pin of nothing and the unpin of a pin another domain took.";
            attribute :>> criterion = "Pages pinned through a translated domain are
                found at their device addresses while pinned and not after; a pin of
                no frames and an unpin by another domain are refused (the `iommu`
                pin line's 2 refusals as specified).";
            attribute :>> parent = ("O.DMA", "ASR-4");
        }
        requirement <'H.DMA.8'> unpinnedBeforeReused : ItemHighLevel {
            attribute :>> statement = "Unpinning shall complete the unit's
                invalidation before the frame or a table the unpin emptied is
                reused, and a unit that never completes it shall leave both held.";
            attribute :>> criterion = "A table an unpin empties returns to the frame
                allocator only after the unit has answered the invalidation that
                covers it, and a unit made never to answer keeps the pin's frames and
                the table out of the allocator.";
            attribute :>> parent = ("O.DMA", "ASR-4");
        }
        requirement <'H.DMA.9'> aDeviceRaisesOnlyItsOwnVectors : ItemHighLevel {
            attribute :>> statement = "Where the machine's interrupts are isolated, a
                device shall raise only the interrupt vectors minted for it: a
                message in compatibility format, or naming another function's
                remapping entry, shall be refused, whatever vector or delivery
                mode it asks for.";
            attribute :>> criterion = "On x86-64 under KVM and TCG, edu's forged
                compatibility-format messages to 0xFC and as an NMI, and its message
                naming another function's entry, are refused with faults 0x25 and
                0x26 and arrive nowhere; the console's line is delivered only
                through its own entry; a device marked for isolated interrupts is
                refused vectors while they are not (the remap lines). AArch64 under
                GICv2m, ARMv7-A and a machine without VT-d interrupt remapping are
                its stated residuals.";
            attribute :>> parent = ("O.DMA", "ASR-4");
        }
        requirement <'H.DMA.4'> deadDriversPinsQuarantined : ItemHighLevel {
            attribute :>> statement = "Frames a driver pinned shall not be reused
                after the driver dies until its replacement announces itself, and the
                frames so held shall be bounded.";
            attribute :>> criterion = "A dead driver's pin is quarantined, a pin past
                twice the device's pin budget, its quarantine counted, is refused
                and taken again once the quarantine is released, and a live
                driver's pin is given back (the `iommu` pin budget line).";
            attribute :>> parent = ("O.DMA", "O.QUOTA");
        }
        requirement <'H.DMA.5'> registersOnlyThroughApertures : ItemHighLevel {
            attribute :>> statement = "A driver shall reach device registers only
                through an I/O mapping of an aperture it holds, and an aperture that
                is not whole pages, or that covers the MSI-X table or pending-bit
                array of a function whose MSI-X the kernel may enable, shall be
                withheld; a function whose MSI-X the kernel never enables has its
                MSI-X Enable held at 0.";
            attribute :>> criterion = "The `devices` line counts the apertures
                withheld for partial pages and for MSI-X ranges; a mapping of a
                withheld range is refused; a program reaches only the aperture it
                was given (the `handles` line); a held-off function's Enable reads 0
                and is refused when it reads 1 (the `msix-off` line).";
            attribute :>> parent = ("O.DMA", "O.CAPABILITY", "ASR-4");
        }
        requirement <'H.DMA.10'> noClientReachesAnUntranslatedGpu : ItemHighLevel {
            doc /* docs/INTEL-GPU.md section 4.4, the isolation rule D4 as the
                 * certification consultant approved it (ledger 2026-10-18
                 * line 2352, (a) to (d)). The GPU executes what programs hand
                 * it, so without translation one bad page-table entry is DMA
                 * anywhere. Its driver, trusted like the kernel in that mode
                 * (VULNERABILITY-ANALYSIS V-03), may still run its own
                 * commands; that is the driver's property, not evidence. */
            attribute :>> statement = "While the unit behind the Intel integrated
                GPU does not translate its DMA, the TSF shall publish no node
                through which a program can reach that GPU, and the GPU shall be
                driven at all only where the command line says ferrix.intelgpu.";
            attribute :>> criterion = "A HELLO for the Intel GPU's function is
                refused Untranslated with nothing published while its domain does
                not translate, whatever it lists, and taken where it does
                (L.object.192); the GPU is yielded without
                ferrix.intelgpu (L.device.44).";
            attribute :>> parent = ("O.DMA", "ASR-4");
        }
    }

    package Devices {
        doc /* A device served by its drivers one at a time, and stopped
             * between them: O.CAPABILITY and ASR-3 for the claim, O.DMA and
             * ASR-4 for the quiesce. Proposed 2026-09-27 with part 20's
             * low-level requirements, which nothing above them stated. */

        requirement <'H.DEV.1'> servedByItsClaimsAlone : ItemHighLevel {
            attribute :>> statement = "A device shall be claimed through no more of
                its core's control channels at once than the core allows -- one,
                but for the input functions of a USB host, an STM32 board's or a
                PCI xHCI function -- and a claim shall stand until the core lets
                it go.";
            attribute :>> criterion = "A second claim of a node is refused, a
                shared node's claims stop at its limit, and one claim let go leaves
                the others (the `services` line).";
            attribute :>> parent = ("O.CAPABILITY", "ASR-3");
        }
        requirement <'H.DEV.2'> refusedUnderALiveDriver : ItemHighLevel {
            attribute :>> statement = "A quiesce shall be refused while a live
                driver serves the device.";
            attribute :>> criterion = "A quiesce of the device a running block
                driver serves answers BAD_STATE (the `blk-ring` line). And with kernel objects alone, on every profile, the `item dev` line (syscall/rehome_check.rs::check_quiesce), against a server of the check's own: a real ring's answer stays the `blk-ring` line.";
            attribute :>> parent = ("O.DMA", "ASR-4");
        }
        requirement <'H.DEV.4'> stoppedBeforeItAnswers : ItemHighLevel {
            attribute :>> statement = "A quiesce shall answer success only once
                every core has let the device go and the function's bus mastering
                is off.";
            attribute :>> criterion = "A quiesce the instant a block driver dies
                answers success, and the function's command register, whose
                bus mastering was turned on while the driver served it as its
                first pin turns it, reads it off (the `blk-ring` line). And with kernel objects alone, on every profile, the `item dev` line (syscall/rehome_check.rs::check_quiesce), against a server of the check's own: a real ring's answer stays the `blk-ring` line.";
            attribute :>> parent = ("O.DMA", "ASR-4");
        }
        requirement <'H.DEV.3'> aRestartedDriverKeepsItsName : ItemHighLevel {
            attribute :>> statement = "A device a driver started again serves shall
                be published under the lowest number its core has free, so that it
                takes back the name its predecessor had.";
            attribute :>> criterion = "A number given back is the next taken (the
                `services` line); a GPU driver killed and restarted is card0
                again (`xtask test-restart`).";
            attribute :>> parent = "P.2";
        }
        requirement <'H.DEV.5'> powerLimitsOnlyThroughTypedCalls : ItemHighLevel {
            attribute :>> statement = "A program shall change the processor's VR
                current limit only through the kernel's typed calls on the power
                claim, which only the driver of the power node can make, and only
                within the bounds the kernel holds for the processor's model.";
            attribute :>> criterion = "cargo xtask test-power: no node without
                the word or on a processor the table does not name; on the fake,
                the driver's writes are the kernel's typed ones, a second claim
                and a copy of the claim are refused.";
            attribute :>> parent = ("O.CAPABILITY", "ASR-3");
        }
        requirement <'H.DEV.6'> firmwareLimitsComeBack : ItemHighLevel {
            attribute :>> statement = "The kernel shall put firmware's VR current
                limit back when the claim's holder goes, its lease lapses, the
                kernel's thermal backstop trips, a write does not read back, and
                at a power-off, a reset and a panic.";
            attribute :>> criterion = "cargo xtask test-power: the fake's raise
                is restored after the driver stops renewing and after it exits;
                stage 3 drives every other cause on the fake.";
            attribute :>> parent = ("O.FAILSAFE", "ASR-6");
            attribute :>> scope = "personality=kernel";
        }
        requirement <'H.DEV.9'> bindRightOnKeptHandleOnly : ItemHighLevel {
            attribute :>> statement = "The kernel shall mint the right to attach a
                function to an IOMMU domain only on the handle devmgr keeps of a
                device's pair, in a kernel whose nodes need it, and no call shall
                name, pass or map an IOMMU domain, unit or table.";
            attribute :>> criterion = "The rights' compile-time assertion; the
                stage 10 authority check; L.device.66, 67, 71.";
            attribute :>> parent = ("O.CAPABILITY", "ASR-3");
        }
        requirement <'H.DEV.10'> nothingGivenBeforeTheBind : ItemHighLevel {
            attribute :>> statement = "Under explicit binding an aperture, a
                vector or a pin shall be given only after the node was bound by
                the holder of the right, and a PCI function shall become a bus
                master only after that bind; a device tree or virtio-mmio node
                has no master enable, and its limit is the refusal of those
                three.";
            attribute :>> criterion = "The stage 10 authority check on made-up
                nodes and on an idle real PCI function; L.device.68, 69, 72.";
            attribute :>> parent = ("O.CAPABILITY", "ASR-3");
        }
        requirement <'H.DEV.11'> iommuInNoAperture : ItemHighLevel {
            attribute :>> statement = "IOMMU registers and tables shall be in no
                aperture a device node gives.";
            attribute :>> criterion = "device::check::check_iommu_held on every
                boot; L.device.70, 73.";
            attribute :>> parent = ("O.CAPABILITY", "ASR-3");
        }
        requirement <'H.DEV.7'> genericTreeNodesPublished : ItemHighLevel {
            attribute :>> statement = "On a machine described by its device tree,
                the kernel shall publish every enabled node that has a compatible,
                sits on memory-mapped buses and is not kernel-owned, and that no
                binding the kernel knows and no virtio-mmio transport already
                holds, as a generic node whose identity -- compatible list, path,
                references and subtree -- is data the kernel does not interpret;
                so that a driver for it needs no change to the kernel.
                Only personality=user publishes real nodes: present and desktop
                publish none, and every profile's check holds this on made-up trees.";
            attribute :>> criterion = "cargo xtask test-driver-model: on one
                kernel ELF whose sha256 is recorded before the test exists, QEMU
                virt's PL031 under a made-up compatible is published, devmgr
                matches it by that compatible from its image-time table and
                checks its driver's requirement table, and the driver reads the
                device's identification, its counter and its match interrupt
                through its own aperture and vector; with the clock's provider
                gone it is not started and devmgr names the reference (D13).
                Stage 10's check holds a made-up tree to the publication rules on
                every boot.";
            attribute :>> parent = ("O.CAPABILITY", "ASR-3");
        }
        requirement <'H.DEV.8'> kernelOwnedNodesExcludedAndSealed : ItemHighLevel {
            attribute :>> statement = "A device-tree node the kernel uses, a node
                under one, or a node whose registers share a page with what the
                kernel uses, shall never be published; the set shall be fixed by
                one registration that is sealed before anything is published; and
                a node a kernel-owned node depends on through clocks, resets,
                power domains, pin control, supplies or interconnects, directly
                or transitively, shall be published flagged KERNEL_DEPENDS.
                Only personality=user publishes real nodes: present and desktop
                publish none, and every profile's check holds this on made-up trees.";
            attribute :>> criterion = "Stage 10's check: on a made-up tree the
                console and a node overlapping its page are kernel-owned, its
                clock and that clock's clock are flagged, and a claim after the
                seal is refused; each with a gate.sh control that fires.";
            attribute :>> parent = ("O.CAPABILITY", "ASR-3");
        }
    }

    package Traps {
        doc /* The system call boundary and the exceptions a program raises:
             * O.VALIDATE and ASR-7 (FPT_TDC.1), with O.ISOLATE for what a
             * program may leave in the registers the kernel is entered with. */

        requirement <'H.TRAP.1'> userRangesChecked : ItemHighLevel {
            attribute :>> statement = "Every pointer and length a system call is
                given shall be checked to lie wholly within the user half before any
                access through it, and a range that does not shall be refused with
                EFAULT.";
            attribute :>> criterion = "Each system call given a kernel-half pointer,
                a range that wraps past the user half's end and a null pointer is
                refused EFAULT, with 0 accesses made.";
            attribute :>> parent = ("O.VALIDATE", "ASR-7");
        }
        requirement <'H.TRAP.2'> unmappedUserMemoryIsEfault : ItemHighLevel {
            attribute :>> statement = "An access to user memory on a system call's
                behalf that meets an unmapped or protected page shall return EFAULT
                to the caller and shall not fault the kernel.";
            attribute :>> criterion = "Copies to an unmapped and to a read-only user
                page, and from an unmapped one, each return EFAULT, and the boot goes
                on to FERRIX-BOOT-OK.";
            attribute :>> parent = ("O.VALIDATE", "ASR-7");
        }
        requirement <'H.TRAP.3'> indicesClampedUnderSpeculation : ItemHighLevel {
            attribute :>> statement = "Every table index a program chooses shall be
                clamped at the system call boundary so that it cannot be used out of
                bounds under speculation, and each processor's speculation controls
                shall be applied and read back.";
            attribute :>> criterion = "The boot reads the speculation defences back
                on every one of the N online processors (the `cpu` line), and the
                `--mitigations off` build is the only one without the clamps.";
            attribute :>> parent = ("O.ISOLATE", "O.VALIDATE");
        }
        requirement <'H.TRAP.4'> userFaultsBecomeSignals : ItemHighLevel {
            attribute :>> statement = "A processor exception a user-mode instruction
                raises shall end in a signal to the faulting thread, the one Linux
                sends for it, and shall not stop the kernel.";
            attribute :>> criterion = "A divide error, an invalid opcode, an unmapped
                read, a privileged instruction, a floating-point exception and a read
                past a mapped file's end end their programs with SIGFPE, SIGILL,
                SIGSEGV, SIGSEGV, SIGFPE and SIGBUS, 6 of 6 (the `fault` line).";
            attribute :>> parent = ("O.ISOLATE", "ASR-1");
        }
        requirement <'H.TRAP.5'> signalReturnCannotRaisePrivilege : ItemHighLevel {
            attribute :>> statement = "Restoring a signal frame a program supplies
                shall not raise its privilege: the restored mode, segment selectors,
                interrupt masks and I/O privilege shall be the user's whatever the
                frame holds, and a return address outside the user half shall be
                refused.";
            attribute :>> criterion = "A sigreturn through frames asking for kernel
                mode, masked interrupts, I/O privilege and a kernel-half return
                address resumes the program in user mode with user flags, or ends it
                with SIGSEGV, on each architecture: 0 in kernel mode.";
            attribute :>> parent = ("O.VALIDATE", "O.ISOLATE", "ASR-7");
        }
        requirement <'H.TRAP.6'> entryTrustsNoUserState : ItemHighLevel {
            attribute :>> statement = "On every entry from user mode the kernel shall
                establish its own stack and per-processor state before using either,
                whatever the program left in its registers, including for an
                exception taken on the entry path itself.";
            attribute :>> criterion = "Breakpoints on the system call entry and on
                its return, and an NMI taken with interrupts masked, each run on the
                kernel's own stack with its own per-processor base, and the program
                exits 42 (the `debug` and `nmi` lines, x86-64).";
            attribute :>> parent = ("O.ISOLATE", "O.FAILSAFE");
        }
        requirement <'H.TRAP.7'> onlyUserSelectors : ItemHighLevel {
            attribute :>> statement = "A program shall load only the segment
                selectors meant for user mode: one naming a kernel descriptor, the
                TSS, the LDT or a forged thread-local descriptor shall be refused.
                x86-64 only.";
            attribute :>> criterion = "7 user selectors load at RPL 3 and 18 others
                are refused (the `gdt` line).";
            attribute :>> parent = ("O.ISOLATE", "O.VALIDATE");
        }
        requirement <'H.TRAP.8'> compatibilityModeAsLinux : ItemHighLevel {
            attribute :>> statement = "A 32-bit x86 program shall run in ring 3 in
                compatibility mode, in Linux's user segments and its own
                thread-local descriptors, and shall enter the kernel only through
                int $0x80, answered as i386 Linux answers it. x86-64 only.";
            attribute :>> criterion = "An ELF32 i386 program's calls through int
                $0x80 answer as i386 Linux's do and it exits 42; a 64-bit program's
                int $0x80 is an i386 call; SYSCALL from 32-bit code answers -ENOSYS
                or is #UD, and SYSENTER ends the program (the first `i386` line).";
            attribute :>> parent = ("O.ISOLATE", "G.5");
        }
        requirement <'H.TRAP.9'> signalFramesAsLinux : ItemHighLevel {
            attribute :>> statement = "A 64-bit program's signal handler shall be
                entered on a frame in Linux's layout, and its return shall resume
                the registers and mask the frame holds.";
            attribute :>> criterion = "The 64-bit signal program's SA_SIGINFO
                handler is entered with the signal, the siginfo and the ucontext, a
                register it changes through the frame comes back through
                rt_sigreturn, and the mask after the return is empty: exit 77 (the
                `signals` line).";
            attribute :>> parent = "G.3";
        }
        requirement <'H.TRAP.10'> registersAsTheAbiSays : ItemHighLevel {
            attribute :>> statement = "A program's registers shall pass the kernel
                as its ABI says: a call's arguments are read from its argument
                registers and its result returned in its return register, a fork
                child resumes from its parent's registers with the call answering
                zero, and a program started or replaced begins at its entry with its
                start argument and no kernel value in any register.";
            attribute :>> criterion = "A call with six arguments answers from all
                six; a fork child's registers are its parent's with the return
                register zero; a program started with an argument finds it, and one
                that ORs its registers on entry finds nothing else set, for each
                ABI.";
            attribute :>> parent = ("G.4", "G.5");
        }
        requirement <'H.TRAP.11'> unknownCallsAreEnosys : ItemHighLevel {
            attribute :>> statement = "A system call number no table carries shall
                be refused with ENOSYS, never answered by a handler or a fault.";
            attribute :>> criterion = "0xDEAD, usize::MAX and usize::MAX - 1, each
                dispatched as a native call through the registered entry, are
                answered -38, 3 of 3. And with kernel objects alone, on every profile, the `item` line (syscall/rehome_check.rs::check_an_unknown_number_is_enosys).";
            attribute :>> parent = "O.VALIDATE";
        }
        requirement <'H.TRAP.12'> decodedByTheEntrysTable : ItemHighLevel {
            attribute :>> statement = "A system call's number shall be decoded
                through the table of the architecture it was built for.";
            attribute :>> criterion = "Of getpid's numbers in the three tables,
                exactly the running architecture's decodes to getpid, and
                dispatching it answers a pid above zero.";
            attribute :>> parent = "O.VALIDATE";
        // H.TRAP.13 to H.TRAP.15 were added by W-8 step 4 (console): the kernel
        // log, which syslog(2) and a log control channel read (T.CONFUSE path 6
        // of VULNERABILITY-ANALYSIS.md), and a program's output on the console.
        requirement <'H.TRAP.13'> logReadsStayInTheLog : ItemHighLevel {
            attribute :>> statement = "A read of a log ring -- the kernel log is one
                -- shall copy into the reader's buffer, up to its length, only bytes
                the ring recorded, in order from the reader's cursor or from the
                oldest byte kept if that is later, and shall count as lost exactly
                the bytes it skips or finds replaced while it copied.";
            attribute :>> criterion = "On a 64-byte ring of the log check's own given
                100 bytes, a reader at 0 is told 37 lost and given the last 63 in
                order across a 10-byte read and a longer one, and 200 bytes later is
                told 137 lost and given 63; while two writers record 20,000 bytes each
                into a 256-byte ring, a reader reads only bytes they wrote, and the
                bytes it read and was told it lost come to exactly 40,000 (the `log`
                line).";
            attribute :>> parent = ("O.VALIDATE", "O.ISOLATE");
        }
        requirement <'H.TRAP.14'> programOutputAsWritten : ItemHighLevel {
            attribute :>> statement = "A program's write to the console shall reach
                the port byte for byte in the order written, each bare newline as CRLF
                unless the program turned output processing off.";
            attribute :>> criterion = "A write of text holding bare newlines reaches
                the port with CRLF for each, and the same write with output processing
                off with LF alone, every other byte the same and in order.";
            attribute :>> parent = "G.5";
        }
        requirement <'H.TRAP.15'> theLogHoldsWhatWasSent : ItemHighLevel {
            attribute :>> statement = "The kernel log shall hold every byte the
                console is given to send, a kernel line or a program's output, as it
                was written and before a newline becomes CRLF, except the lines the
                kernel sends unlogged.";
            attribute :>> criterion = "Over a boot, the kernel log read from its
                oldest byte holds, in order and without CRs, every kernel line the
                serial log holds but the unlogged ones, and every program's output.";
            attribute :>> parent = "G.5";
        }
        requirement <'H.TRAP.16'> aRegisteredFilterOnlyTakesAwayFromACall : ItemHighLevel {
            attribute :>> statement = "A look a personality registers with the core at
                its system call entries, before any answer of the entry's own, shall be
                able to make a call do only less than it could: let it go on, fail it
                with an errno the core bounds to 0 to 4095, or have the core give its
                registers back as the program made it, a value the core takes from the
                caller's own registers. It shall have no way to
                answer with anything else, so that it cannot start a program or choose
                what a program's registers hold; a filter that must end the program does
                so through the paths exit and a fatal signal already take. It shall be
                asked about every call of every entry
                once, first, with the entry's own architecture token and the
                instruction after the call, and nothing registered shall change what
                the core does.";
            attribute :>> criterion = "Driven through each entry this architecture
                has, every call the entry answers itself reaches a test-only filter
                once, before that answer, and the filter's value is the one the program
                gets; an int $0x80 call carries i386's token; a number with bits above
                the 32nd set is judged as its low half and dispatched as no call; a
                native-range call carries a token of its own; an errno a filter answers is
                cut to 4095 by the core, and 512 is an ordinary errno (the `seccomp`
                line).";
            attribute :>> parent = ("O.ISOLATE", "O.VALIDATE");
        }
        requirement <'H.TRAP.17'> barrierOutsideASpeculationDomain : ItemHighLevel {
            attribute :>> statement = "A switch between the address spaces of two
                programs not in one speculation domain shall issue the predictor
                barrier; a switch between two address spaces of one domain shall not.
                A domain is a job marked at its creation by the holder of MANAGE on
                its parent, and holds only the programs born in it that have not
                left it.";
            attribute :>> criterion = "The `domain` line: switches inside one
                domain decide no barrier, and switches to and from no domain,
                another domain, a domain inside it, a mover, a leaver and a sharer
                decide one each way, on every architecture the suite boots.";
            attribute :>> parent = "O.ISOLATE";
        }
        requirement <'H.TRAP.19'> oneThreadACoreUnderSmtOff : ItemHighLevel {
            doc /* smt=off (BUILD-FLAGS.md section 3.1 DF4): siblings share a
                core's predictors and buffers, so a build that claims one thread
                a core keeps every other thread of a core out of kernel and
                program code, and sets each up to take a machine check so a
                broadcast does not shut the machine down (F-73). The
                consultant's ledger 2563, condition (4). */
            attribute :>> statement = "Under smt=off no two hardware threads of one
                core shall run kernel or program code: each thread of a core but
                one shall be parked by the kernel, set up to take a machine check,
                or absent; and a topology the kernel cannot read shall stop the
                boot rather than be read as one thread a core.";
            attribute :>> criterion = "Stage 4's `smt` line under smt=off, on every
                architecture: no two online processors of one core, every parked
                thread reported with CR4.MCE set (x86-64), and no core of the PPTT
                or cpu-map listing two threads of processors that run work (Arm);
                with one sibling started for work, or a parked thread's CR4.MCE
                left clear, or two threads a core in the Arm tables, it fails by
                name.";
            attribute :>> parent = "O.ISOLATE";
        }
        requirement <'H.TRAP.20'> faultsGoToTheirSupervisorsFirst : ItemHighLevel {
            attribute :>> statement = "A fault a program takes in user mode that its
                address space does not resolve shall be offered to the supervisors
                attached to its process and to its jobs, nearest first, before the
                personality sees it. Each shall answer resume, with registers checked
                as sigreturn checks a frame, kill or hand on, within a bounded wait;
                a fault unanswered, or handed on past the last, shall take the path
                it takes with no supervisor. Only a holder of SUPERVISE attaches one,
                and no process raises its ids while one watches it.";
            attribute :>> criterion = "The `exceptions` line on every boot: a fault
                resumed with written registers exits as written, forged registers are
                refused, KILL ends the process, a hand on reaches the job's channel at
                level 1, an unanswered fault ends with SIGSEGV after its timeout, an
                exception closed or held by a supervisor that died is handed on at
                once; a cgroup move into a supervised job is EBUSY (the `cgroups`
                line).";
            attribute :>> parent = ("O.CAPABILITY", "O.ISOLATE");
        }
        requirement <'H.TRAP.21'> restrictedModeRunsAProgramAndComesBack : ItemHighLevel {
            attribute :>> statement = "The kernel shall provide a restricted mode: a thread of a shared
                process shall run a program context and come back, the same thread
                with no scheduler decision and no message, on a system call, an
                unresolved fault or a kick, with the context held by the kernel.";
            attribute :>> criterion = "The `regions` line on every boot of x86-64: restricted-check holds
                every case of K1 §10.";
            attribute :>> parent = ("O.ISOLATE");
        }
        requirement <'H.TRAP.22'> aContextIsCheckedAsSigreturnIs : ItemHighLevel {
            attribute :>> statement = "Every context handed to the kernel for restricted mode shall be
                checked by the rules a signal frame is, refused rather than
                masked, and a refusal shall change nothing.";
            attribute :>> criterion = "The `regions` line on every boot of x86-64: restricted-check holds
                every case, its forged contexts each refused INVALID_ARGS, then a
                good one running.";
            attribute :>> parent = ("O.ISOLATE");
        }
        requirement <'H.TRAP.23'> nothingOfTheRegionFromRestrictedMode : ItemHighLevel {
            attribute :>> statement = "Nothing of a partition's shared region shall be reachable from
                restricted mode: not readable, writable or executable.";
            attribute :>> criterion = "The `regions` line on every boot of x86-64: restricted-check holds
                every case; load, store and fetch at the region exit FAULT, and
                the sweep of the restricted root finds none of the region's
                entries or frames.";
            attribute :>> parent = ("O.ISOLATE");
        }
        requirement <'H.TRAP.24'> restrictedExitKeepsVectorsAndTheBarrier : ItemHighLevel {
            attribute :>> statement = "A program's whole vector state shall survive every exit from
                restricted mode, and each exit shall keep the speculation rule the
                build selects, with the barrier counted.";
            attribute :>> criterion = "The `regions` line on every boot of x86-64: restricted-check holds
                every case; the vector case, and one barrier decided per exit,
                none per entry, under `exit`.";
            attribute :>> parent = ("O.ISOLATE");
        }
    }

    package Boot {
        doc /* What the kernel does with what it is handed before anything runs
             * above it, and what a boot claims: O.FAILSAFE and ASR-6 (FPT_FLS.1),
             * and O.ISOLATE for the layout. */

        requirement <'H.BOOT.1'> handOffVerified : ItemHighLevel {
            attribute :>> statement = "Before using what the loader hands over, the
                kernel shall verify the memory map, the page tables and its own
                placement, and shall halt with a diagnostic if any check fails.";
            attribute :>> criterion = "Stage 1 reports the hand-off verified on
                every architecture; a hand-off with a field made inconsistent ends in
                the catalogued panic, not in a boot.";
            attribute :>> parent = ("O.FAILSAFE", "ASR-6");
        }
        requirement <'H.BOOT.2'> aBootSaysWhetherItChecked : ItemHighLevel {
            attribute :>> statement = "Every boot shall run every stage's self-checks
                unless told not to, and shall print FERRIX-BOOT-OK only when all of
                them passed; a boot that skipped them shall end with
                FERRIX-BOOT-UNCHECKED instead.";
            attribute :>> criterion = "`cargo xtask test-boot` finds FERRIX-BOOT-OK
                on each architecture; a boot with `ferrix.checks=skip` ends with
                FERRIX-BOOT-UNCHECKED and never prints FERRIX-BOOT-OK.";
            attribute :>> parent = ("O.FAILSAFE", "ASR-6");
        }
        requirement <'H.BOOT.3'> layoutIsRandomised : ItemHighLevel {
            attribute :>> statement = "The kernel shall run with its image, direct
                map and vmap arena at the offsets the loader drew from the firmware's
                random-number protocol, and shall verify the move at stage 1.";
            attribute :>> criterion = "Two boots of one image report two different
                layouts (`cargo xtask test-kaslr`), and stage 1 verifies the slide
                each reports.";
            attribute :>> parent = "O.ISOLATE";
        }
        requirement <'H.BOOT.4'> firmwareTablesBounded : ItemHighLevel {
            attribute :>> statement = "The kernel shall refuse an ACPI table, a
                device tree, or an SMBIOS entry point or structure table whose
                declared length is shorter than its header or reaches beyond the
                memory mapped for it, rather than read past it.";
            attribute :>> criterion = "The ACPI, device-tree and SMBIOS parsers' host
                tests feed truncated, oversized and misaligned tables and each is
                refused with its error, 0 read out of bounds; the kernel refuses a
                table outside the direct map, and an SMBIOS copy outside its region
                of the memory map.";
            attribute :>> parent = ("O.FAILSAFE", "ASR-6");
        }
        // Added by W-8 step 4 (smp): the processors a boot claims, which no
        // requirement above said.
        requirement <'H.BOOT.5'> everyProcessorComesUp : ItemHighLevel {
            attribute :>> statement = "Every processor firmware describes shall be
                running kernel code on its own per-processor record before the
                scheduler starts, or the boot shall halt with a diagnostic saying
                which step failed.";
            attribute :>> criterion = "On each configuration `cargo xtask test-boot`
                boots, the `cpus` line counts as many processors online as firmware
                described (4 of 4 on x86-64 and AArch64, 2 of 2 on ARMv7-A at `--smp
                2`); a secondary made never to report in ends the boot in FX-0402.";
            attribute :>> parent = ("O.FAILSAFE", "ASR-6");
        }
        requirement <'H.BOOT.6'> endsPoweredOff : ItemHighLevel {
            attribute :>> statement = "When init exits and ferrix.onexit asks for
                nothing else, the machine shall power itself off after the console
                has drained.";
            attribute :>> criterion = "After init exits, QEMU exits by itself within
                the grace, with status 0 or 33, and init's exit line is in the log.";
            attribute :>> parent = "O.FAILSAFE";
        }
        requirement <'H.BOOT.7'> resetsWhenAsked : ItemHighLevel {
            attribute :>> statement = "When init exits and ferrix.onexit=reset asks
                for it, the machine shall restart from firmware after the console
                has drained.";
            attribute :>> criterion = "Under ferrix.onexit=reset the kernel says it
                is resetting and the loader's banner is printed again after it.";
            attribute :>> parent = "O.FAILSAFE";
        }
        requirement <'H.BOOT.8'> consoleCarriesTheSession : ItemHighLevel {
            attribute :>> statement = "The serial console shall carry the kernel's
                lines out, and a person's typed bytes in to the program reading
                them, in order and without waiting unboundedly on the port.";
            attribute :>> criterion = "test-boot reads every stage's line and
                FERRIX-BOOT-OK from the serial port, and test-jobs's 18 typed steps
                each have their answer after them.";
            attribute :>> parent = "O.FAILSAFE";
        // Added by W-8 step 4 (console): the KASLR half of F-31 is worth only as
        // much as nothing a program reads gives the layout away, and the kernel
        // log is readable (console::write_unlogged says which lines stay out).
        requirement <'H.BOOT.9'> theLogHoldsNoLayout : ItemHighLevel {
            attribute :>> statement = "The kernel log shall hold neither the KASLR
                slide nor any kernel virtual address the kernel prints: a panic's
                slide and backtrace, a fatal trap's registers, stage 2's placement of
                the image, the direct map and the page array, and the sweeps' failure
                lines shall go to the port and never into the log.";
            attribute :>> criterion = "After a boot, and after a panic with a
                backtrace, the kernel log read whole holds 0 occurrences of the slide
                or of any image, direct-map or vmap address the serial log printed.";
            attribute :>> parent = "O.ISOLATE";
        }
        requirement <'H.BOOT.15'> pid1IsWhatTheImageNames : ItemHighLevel {
            attribute :>> statement = "Pid 1 shall be the program the boot names: the
                file ferrix.init= names, else the commands or the program the boot
                initramfs carries under .ferrix/init, else /sbin/init; an input that
                cannot be one shall be refused with a line saying which and why,
                and never replaced by a guess.";
            attribute :>> criterion = "Each way of starting pid 1 boots as named
                (test-shell, test-vfs, test-init); malformed inputs are each refused
                and taken as absent (L.init.1 to L.init.3); and none is unpacked
                into a root, which SAFETY-MANUAL AoU-24 assumes of the unpacker.";
            attribute :>> parent = "O.FAILSAFE";
        }
        // Added by D1 (docs/DMI.md; consultant ledger line 1339).
        requirement <'H.BOOT.16'> firmwareIdentityOnlyFromAValidatedTable : ItemHighLevel {
            attribute :>> statement = "The kernel shall show the firmware's identity
                only from an SMBIOS table it validated, with the values the table
                holds, and nothing when there is none or it does not validate; the
                boot shall go on either way.";
            attribute :>> criterion = "A test boot under QEMU with -smbios accepts the
                table and names exactly the vendor and the product QEMU was given,
                and no serial or UUID of it appears in the log; forged copies are
                each refused by name at boot, and refused tables leave nothing
                shown.";
            attribute :>> parent = ("O.FAILSAFE", "ASR-6");
        }
    }

    package Quotas {
        doc /* What a job, with every job beneath it, may hold at once:
             * O.QUOTA (FRU_RSA.1), against T.EXHAUST. */

        requirement <'H.QUOTA.1'> taskLimit : ItemHighLevel {
            attribute :>> statement = "Creating a task in a job that, with the jobs
                beneath it, holds its task limit shall be refused, and no task shall
                be counted beyond the limit.";
            attribute :>> criterion = "A fork loop in a job limited to 8 tasks is
                refused at the limit, 0 tasks beyond it (the `quota` line).";
            attribute :>> parent = "O.QUOTA";
        }
        requirement <'H.QUOTA.2'> memoryLimit : ItemHighLevel {
            attribute :>> statement = "A job's programs shall not hold more memory
                than the job's limit, counting the frames of their address spaces
                and their page tables together with every job beneath it; a sibling
                job shall be unaffected.";
            attribute :>> criterion = "Faults in a job limited to 48 pages' worth
                are refused when the next page would not fit, and the refusal is
                counted, while a sibling job faults 48 pages in (the `quota`
                line).";
            attribute :>> parent = "O.QUOTA";
        }
        requirement <'H.QUOTA.3'> objectLimit : ItemHighLevel {
            attribute :>> statement = "Creating a channel or a port in a job at its
                object limit shall be refused, and no object shall be counted beyond
                the limit.";
            attribute :>> criterion = "Object creation in a job limited to 5 objects
                is refused at the limit, 0 objects beyond it (the `quota` line).";
            attribute :>> parent = "O.QUOTA";
        }
        requirement <'H.QUOTA.4'> chargesComeBack : ItemHighLevel {
            attribute :>> statement = "Every charge against a job shall be returned
                when the resource it paid for is freed, and a job's quota slot shall
                be given back when the job goes.";
            attribute :>> criterion = "After the quota checks every counter of their
                jobs is back to zero, and as many quota slots are in use as before
                them (the `quota` line).";
            attribute :>> parent = "O.QUOTA";
        }
        requirement <'H.QUOTA.5'> limitsAreHierarchical : ItemHighLevel {
            attribute :>> statement = "A limit set on a job shall bound it together
                with every job beneath it, and a charge refused at any level shall
                leave no level charged.";
            attribute :>> criterion = "A charge that would pass a grandparent's limit
                is refused although the child's own limit allows it, and each level's
                counter reads as before the attempt.";
            attribute :>> parent = "O.QUOTA";
        }
        // Added by the low-level pilot on object/ (W-8 step 3), like H.OBJ.10-13.
        // The memory a killed or ended process held goes back before a
        // parent can see the end: the load's Process::release unmaps it, as
        // Linux's exit_mm (F-91, ledger 2962). The kill's claim leans on that
        // load-side rule, whose evidence is stage 13's OOM check, until the
        // personality is lifted out (MICROKERNEL.md).
        requirement <'H.QUOTA.6'> oomKillIsScoped : ItemHighLevel {
            attribute :>> statement = "A user page fault refused by a job's memory
                limit shall end a process in the job whose limit was full or beneath
                it, never one outside it, count the kill in that job and every job
                above it, and retry the fault.";
            attribute :>> criterion = "A program writing 8 MiB in a job limited to 1
                MiB ends by SIGKILL while a larger process in a sibling job lives;
                exactly 1 process is killed; memory.events counts one OOM kill in the
                job and its parent and none in the sibling. On Bare, present and desktop (bare_side_check): a_limit_ends_its_own, its status the kill's.";
            attribute :>> parent = ("G.8", "O.QUOTA");
        }
        // Split out of H.QUOTA.2 and H.QUOTA.4 by the pilot, for one check each.
        requirement <'H.QUOTA.7'> kernelHeapIsCharged : ItemHighLevel {
            attribute :>> statement = "The kernel heap the Linux personality keeps
                for a job's programs shall be charged against the job's memory
                limit, and every byte of it returned when it is freed; a sibling job
                shall be unaffected.";
            attribute :>> criterion = "At a 32 KiB limit each kind of personality
                object is refused one past its count with ENOMEM (ENOLCK for a lock)
                while a sibling makes one, and with them gone every byte charged has
                come back (the `kmem` line).";
            attribute :>> parent = "O.QUOTA";
        }
        // Split out of H.QUOTA.1 and H.QUOTA.3 by the pilot: the part no check proves.
        requirement <'H.QUOTA.8'> taskLimitIsAnswered : ItemHighLevel {
            attribute :>> statement = "A creation the task limit refuses shall be
                answered as Linux and the native ABI answer it -- a fork with
                EAGAIN, a native process_create with SHOULD_WAIT -- and the refused
                process shall never start.";
            attribute :>> criterion = "A fork past pids.max is answered EAGAIN and
                counted in pids.events; process_create into a job at its task limit
                is answered SHOULD_WAIT and the job's task count is unchanged.";
            attribute :>> parent = "O.QUOTA";
        }
        requirement <'H.QUOTA.9'> everyObjectIsCounted : ItemHighLevel {
            attribute :>> statement = "Creating a VMO, a job or a pin in a job at
                its object limit shall be refused with NO_MEMORY, and each shall be
                counted as an object for as long as it exists.";
            attribute :>> criterion = "In a job limited to 5 objects and holding 5,
                vmo_create, job_create and vmo_pin are each refused NO_MEMORY, 0
                objects counted beyond the limit, and the job holds 0 once they are
                all closed.";
            attribute :>> parent = "O.QUOTA";
        }
        // Stage 13's controllers (cpu.max, cgroup.freeze, reclaim), 2026-10-01.
        requirement <'H.QUOTA.10'> cpuBandwidthIsBounded : ItemHighLevel {
            attribute :>> statement = "A job's tasks, with those of every job
                beneath it, shall use no more processor time in a period than the
                job's cpu.max allows, and a task kept waiting for the period to
                end shall leave the wait at once for its end, under a personality a kill or a signal.";
            attribute :>> criterion = "A program in a job limited to 20000 of
                100000 microseconds is held to between a twelfth and two thirds of
                a processor with the throttling counted in cpu.stat, and one in a
                job limited to 1000 of 1000000 ends within a quarter of a second
                of its SIGKILL (the `cgroups` line, cpu). On Bare, present and desktop (bare_side_check): a_quota_cuts_a_program_alone and a_throttled_program_leaves_for_its_end; the signal is the load check above.";
            attribute :>> parent = "O.QUOTA";
        }
        requirement <'H.QUOTA.11'> aFrozenJobStops : ItemHighLevel {
            attribute :>> statement = "A process in a job, or beneath one, whose
                cgroup.freeze is set shall run no user code until the job is
                thawed or the process is killed; SIGCONT shall not thaw it, and
                cgroup.events shall say frozen only once every live process
                beneath has stopped.";
            attribute :>> criterion = "A program of three threads in a frozen
                cgroup stops counting, cgroup.events says frozen 1 and wakes its
                poller, SIGCONT changes neither, and thawing restarts its futex
                wait (the `cgroups` line, freeze).";
            attribute :>> parent = "O.QUOTA";
        }
        requirement <'H.QUOTA.12'> reclaimComesBeforeTheKill : ItemHighLevel {
            attribute :>> statement = "A charge refused by a job's memory limit,
                and a program over its memory.high, shall first take back clean
                file cache charged to that job or beneath it, never a sibling's
                and never a child's at or under its memory.min, and read back as
                its source has it, and then the heap of the cached names and
                files nothing else holds charged to that job or beneath it,
                before anything is killed.";
            attribute :>> criterion = "A cgroup reading a file twice its
                memory.high is brought back to it, its sibling's cache untouched,
                every page read back as the source has it, and a read at
                memory.max kills nothing where its clean cache was room (the
                `cgroups` line, reclaim). And a file of a writable btrfs mount cut
                and written again, written back and taken back, reads back as
                written, and a write into part of such a page keeps the page's
                other bytes (the `reclaim` line of test-btrfs; at stage 8 the
                page store over a source that takes cuts; F-116).";
            attribute :>> parent = ("G.8", "O.QUOTA");
        }
        requirement <'H.QUOTA.13'> programsStopAtTheWatermark : ItemHighLevel {
            attribute :>> statement = "A frame for a program's memory or page
                tables shall be refused when taking it would leave fewer frames
                free than the kernel's watermark, whatever job the program is in,
                with nothing taken; the kernel's own allocations shall not be
                refused by it.";
            attribute :>> criterion = "At stage 2, program frames taken until
                refused leave exactly the watermark free; at that count a
                program's page table is refused and a kernel frame and a fresh
                heap page are given; a run of two frames is given at two above it
                and refused at one above with a block of two free; every frame
                comes back (the `watermark` line).";
            attribute :>> parent = ("G.8", "O.QUOTA");
        }
        requirement <'H.QUOTA.22'> machineOomKillIsBounded : ItemHighLevel {
            attribute :>> statement = "A user page fault refused for want of memory
                with no job's memory limit full shall take back clean file cache
                anywhere and retry, a bounded number of times; once that gives back
                nothing or the bound is spent, it shall end the live process with
                the most resident memory anywhere, never pid 1, count the kill in
                that process's job and every job above it, and retry; it shall make
                at most one such kill within a grace period while a victim's memory
                comes back, and fail as it would without a kill after a bounded
                number of answers.";
            attribute :>> criterion = "Stage 5's quota check: with reclaims left and
                clean cache the fault retries and kills nobody; with them spent the
                process with the most resident pages among three in two jobs is
                ended and counted in its job alone; a second kill is not made
                while it ends or within the grace; a fault's last answer refuses.";
            attribute :>> parent = ("G.8", "O.QUOTA");
        }
        // K7, charging that follows the client (docs/microkernel/K7.md; the
        // consultant's OK IF, ledger 2525).
        requirement <'H.QUOTA.14'> chargesFollowTheClient : ItemHighLevel {
            attribute :>> statement = "The VMO commits and new objects a server's
                native calls make while it holds a live ticket shall be charged to
                the job the kernel recorded when it issued the ticket, and to no
                job a server names; a ticket shall stay live until END from either
                side or the close of either end of its channel, the client's
                library ending it when the reply arrives or it gives up.";
            attribute :>> criterion = "Stage 9's ticket check: a ticket names its
                issuer's process and job, adoptions through any other end and of
                ended or unknown ids are refused and audited, an adopted call's
                commits and objects land on the client and none on the server,
                each end stops the charging at the next call, at most 64 tickets
                live on one end, and every counter comes back (the `ticket`
                line).";
            attribute :>> parent = "O.QUOTA";
        }
        // K12 (docs/microkernel/K12.md): a job's reservation beside its
        // limit. K12a held frames and page tables; K12b widened it by the
        // kernel heap's pages (ledger 2550 (4)).
        // A frame retired for a hardware error costs the promise that frame,
        // up to the retired set's capacity: lost memory, stated, not hidden
        // (ledger 5841 R1).
        requirement <'H.QUOTA.15'> aReservationIsThere : ItemHighLevel {
            attribute :>> statement = "A frame of a job's memory or page tables,
                or a page of the kernel heap its objects are made on, taken in
                task context while the job holds fewer frames drawn from its
                reservation than the reservation's size, shall not be refused
                for want of free memory; no other job's frame or object and no
                frame of the kernel's own shall take a frame promised to a
                reservation.";
            attribute :>> criterion = "At stage 2, with a reservation admitted,
                program frames are refused at the watermark beyond the promise
                and the kernel's own at the promise, and the reservation's own
                frames are then given below both up to its size (the `reserve`
                line of stage 2); at stage 9 a reserved job's frames are drawn
                from its reservation and one taken while an interrupt is
                serviced is not (the `reserve` line of stage 9).";
            attribute :>> parent = ("G.8", "O.QUOTA");
        }
        requirement <'H.QUOTA.16'> aReservationIsAdmittedFromFreeFrames : ItemHighLevel {
            attribute :>> statement = "A reservation shall be admitted only while
                the frames free, less the watermark and every outstanding
                promise, cover it, and refused with nothing changed otherwise.";
            attribute :>> criterion = "At stage 2 a reservation one frame past
                what the free frames cover is refused with the promise
                unchanged, and one they cover raises the promise by exactly its
                size (the `reserve` line of stage 2).";
            attribute :>> parent = ("G.8", "O.QUOTA");
        }
        requirement <'H.QUOTA.17'> nobodyElseTakesAReservation : ItemHighLevel {
            attribute :>> statement = "No reclaim for another job, no limit or
                memory.high above a reserved job, and no process or job put
                into its subtree from outside without the RESERVE right shall
                take a frame drawn from its reservation or refuse a charge its
                reservation covers.";
            attribute :>> criterion = "At stage 9 a limit and a memory.high
                above a reserved job are refused, a reclaim for another spares
                its drawn frame, and a job made beneath it from outside without
                RESERVE is refused (the `reserve` line of stage 9 and the native
                refusals).";
            attribute :>> parent = ("G.8", "O.QUOTA");
        }
    }

    package Audit {
        doc /* The audit record of the TSF's own decisions: O.AUDIT (FAU_GEN.1,
             * FAU_GEN.2, FAU_SAR.1, FAU_SAR.2, FAU_STG.1, FAU_STG.4), for
             * P.ACCOUNTABILITY. docs/certification/AUDIT.md is the design. */

        requirement <'H.AUD.1'> gaplessAndStarted : ItemHighLevel {
            attribute :>> statement = "Each audit ring shall number its records
                from zero without a gap, the high-value ring's first being the
                start-up record with the boot's whole audit id and both ring
                lengths; a second start shall change nothing, and a reader asking
                for a record the ring overwrote shall be moved on and told exactly
                how many it lost.";
            attribute :>> criterion = "On a store of four high-value records, the
                start-up record is number 0 and carries the id and lengths; a
                second start is refused; after six grants a read from 0 copies
                records 3 to 6 and reports 3 lost; a read of two from 3 resumes at
                5.";
            attribute :>> parent = "O.AUDIT";
        }
        requirement <'H.AUD.2'> theBootsRecordsPinned : ItemHighLevel {
            attribute :>> statement = "The first twelve system records shall stay
                readable, numbered as the high-value ring numbered them, however
                far that ring has wrapped, and no record after them shall join
                them.";
            attribute :>> criterion = "Thirteen system records and a grant in a
                ring of four: the boot records read back 0, 1, 2, 3, 5, 6, 7, 8, 9,
                10, 11, 12, the ring reports records lost, and a read of the boot
                records from 6 copies 7 and resumes at 13.";
            attribute :>> parent = "O.AUDIT";
        }
        requirement <'H.AUD.3'> refusalsKeptApart : ItemHighLevel {
            attribute :>> statement = "A refusal shall be kept in the refusal ring
                and a record of every other class in the high-value ring, so that
                no flood of refusals can overwrite a grant.";
            attribute :>> criterion = "One record of each of the six classes: the
                refusal alone in the refusal ring, the other five in the
                high-value ring in the order made.";
            attribute :>> parent = "O.AUDIT";
        }
        requirement <'H.AUD.4'> aBudgetIsItsMakers : ItemHighLevel {
            attribute :>> statement = "A job shall be charged, for the fairness of
                the refusal ring, to the budget its maker gave it: its parent's
                for a job its members could make themselves, its own otherwise.";
            attribute :>> criterion = "An anonymous job and one inside it are
                charged to their unit, a cgroup made in a delegated unit to that
                unit, and a cgroup root made in a unit to itself: 6 jobs' budgets
                as given.";
            attribute :>> parent = "O.AUDIT";
        }
        requirement <'H.AUD.5'> aFloodIsCounted : ItemHighLevel {
            attribute :>> statement = "Past 64 refusals charged to one budget in a
                second, the TSF shall count that budget's further refusals rather
                than keep them, and write the count once the second has ended,
                while another budget's refusals and every grant are kept.";
            attribute :>> criterion = "104 refusals from a unit's three jobs keep
                64 between them and, once the second has ended, one suppressed
                record counting 40 under the unit; the delegated unit's refusal in
                the same second is kept, and a grant made before is still read
                with none lost.";
            attribute :>> parent = "O.AUDIT";
        }
        requirement <'H.AUD.6'> anEvictedCountIsWritten : ItemHighLevel {
            attribute :>> statement = "A budget whose fairness window is taken to
                make room for another shall have its count written, not
                dropped.";
            attribute :>> criterion = "A budget one over its limit, then 32 more
                budgets: the first's window is closed and its suppressed record
                counts 1.";
            attribute :>> parent = "O.AUDIT";
        }
        requirement <'H.AUD.7'> theConfigurationRecorded : ItemHighLevel {
            attribute :>> statement = "The boot shall start its audit record with
                the start-up record of the id reads answer, and record whether its
                self-checks run, who starts devmgr, the mitigations it was built
                with, the KASLR state and the build flags it was compiled with,
                as bring-up read them.";
            attribute :>> criterion = "The kernel's boot records begin with the
                start-up record, its id the one reads answer and its lengths 512
                and 4096, and hold the 5 configuration records with bring-up's
                values; the boot is not yet recorded as brought up.";
            attribute :>> parent = "O.AUDIT";
        }
        requirement <'H.AUD.8'> everyDecisionRecorded : ItemHighLevel {
            attribute :>> statement = "Each decision the TSF makes at a recording
                site -- a call its rights refused, a widening refused, a limit's
                refusal, a process made, a job given for a cgroup, a control
                channel given, a job killed, a cgroup killed, an OOM kill, a device
                quiesced, a limit set by handle or by cgroup file, a DMA fault --
                shall be recorded with its outcome and the subject that made it,
                the kernel for the decisions it makes alone.";
            attribute :>> criterion = "At the end of a boot with checks, the
                record holds each of the 12 events the boot's checks provoke, and
                DMA_FAULT where a unit reported a DMA fault, with the outcome of its class
                and its subject; none of the OOM kill, the quiesce and the fault
                names a process; the boot is recorded as brought up.";
            attribute :>> parent = "O.AUDIT";
        }
        requirement <'H.AUD.9'> readByItsHandleAlone : ItemHighLevel {
            attribute :>> statement = "The audit record shall be read only through
                the audit handle with READ, which can be neither duplicated nor
                sent; a read shall copy whole records from a cursor, and a read
                that copies none or cannot copy them out shall leave the cursor,
                the buffer and the reader's position where they were.";
            attribute :>> criterion = "A handle with pid 1's rights reads the boot
                records, the start-up record first with the kernel's id; a count
                of 0 copies nothing and moves nothing; a read into unmapped memory
                is FAULT and counts nothing read; a handle without READ,
                a channel end and a ring that does not exist are refused; the
                handle is not duplicated and not sent.";
            attribute :>> parent = "O.AUDIT";
        }
        requirement <'H.AUD.10'> keptOnTheVolume : ItemHighLevel {
            attribute :>> statement = "A boot with init shall keep its audit record
                on the root volume in a file named by the boot's audit id, holding
                the start-up record, the configuration, and the decisions only a
                boot with init makes.";
            attribute :>> criterion = "svc audit reads back the start-up record
                with the id init named the file by, the checks' configuration as
                run, STARTER_GIVEN, READER_GIVEN, DEVMGR_STARTED by pid 1 and
                ROOT_SWITCHED with pid 1 moved.";
            attribute :>> parent = "O.AUDIT";
        }
        requirement <'H.AUD.11'> nothingLostAtPowerOff : ItemHighLevel {
            attribute :>> statement = "Every record up to a power action shall be
                in the reader's file or on the console: the kernel shall record the
                power action last, say how far the reader read, and print every
                record past that, and a run the ring overwrote as one line.";
            attribute :>> criterion = "At test-init's power-off, init's last read
                is where the kernel saw it stop, and every number from there to
                the power action is printed as unread or in a lost run.";
            attribute :>> parent = "O.AUDIT";
        }
        requirement <'H.AUD.12'> anUncheckedBootSaysSo : ItemHighLevel {
            attribute :>> statement = "A boot that skips its self-checks shall
                record that it did, where a reader outside it can see.";
            attribute :>> criterion = "A boot with ferrix.checks=skip, read back
                through svc audit, holds the checks' configuration record with
                value 0.";
            attribute :>> parent = "O.AUDIT";
        }
        requirement <'H.AUD.13'> aRecordsLayout : ItemHighLevel {
            attribute :>> statement = "An audit record shall be 64 bytes, each
                field little-endian at a fixed offset, so that a reader decodes
                what the kernel wrote.";
            attribute :>> criterion = "A record of distinct bytes encodes to them
                in order at the offsets the layout names and decodes back equal.";
            attribute :>> parent = "O.AUDIT";
        }
    }

    package Failure {
        doc /* The safe state and what brings the kernel to it: O.FAILSAFE and
             * ASR-6 (FPT_FLS.1). SAFETY-MANUAL.md §3 defines the safe state. */

        requirement <'H.FAIL.1'> haltOnInconsistency : ItemHighLevel {
            attribute :>> statement = "On a failed internal consistency check the
                kernel shall stop every other processor, print a diagnostic naming the
                failure and its catalogued explanation, and halt without returning to
                user mode, or, where H.FAIL.5 applies, reset the machine after the
                report.";
            attribute :>> criterion = "A boot told to panic at its end
                (`ferrix.onexit=panic`) ends with the FX-1501 report and no program
                output after it; every panic site in the item has a catalogue entry
                (`check-panic-audit.py`).";
            attribute :>> parent = ("O.FAILSAFE", "ASR-6");
        }
        requirement <'H.FAIL.15'> anOverflowStopsWithAReport : ItemHighLevel {
            doc /* F-103, ledger 7033 A7. H.FAIL.2 says what the allocator gives; this says
                   what the entry does with it. */
            attribute :>> statement = "An overflow of a kernel stack shall stop the
                processor with a report, writing nothing below the stack's guard.";
            attribute :>> criterion = "L.aarch64.91, L.armv7a.30 and L.x86_64.83 verified;
                controls on each architecture: a stack overflowed with another allocation
                directly below it, reached by a store and by an interrupt, reports from
                its own stack and leaves that allocation unchanged.";
            attribute :>> parent = ("O.FAILSAFE", "ASR-6");
        }
        requirement <'H.FAIL.2'> stacksAreGuarded : ItemHighLevel {
            attribute :>> statement = "The allocator every kernel stack comes from
                shall give each an unmapped guard page directly below and above
                it.";
            attribute :>> criterion = "A kernel stack allocated, written at its first
                and last word and freed has the page below and the page above it
                untranslated, and gives back every frame it took.";
            attribute :>> parent = ("O.FAILSAFE", "ASR-6");
        }
        // Split out of H.FAIL.2 by W-8 step 4 (mm and user): the half no check proves.
        requirement <'H.FAIL.3'> overflowIsReported : ItemHighLevel {
            attribute :>> statement = "A kernel stack overflow shall end in the halt
                and diagnostic of the safe state, never in a write below the stack.";
            attribute :>> criterion = "A kernel thread that recurses past its stack
                ends the boot in a report naming the fault -- on x86-64 a double fault
                taken on its own stack (FX-9004) -- on each architecture, 3 of 3.";
            attribute :>> parent = ("O.FAILSAFE", "ASR-6");
        }
        // Added by W-8 step 4 (console): the port every diagnostic above is
        // printed on, when whatever holds its lock never lets go.
        requirement <'H.FAIL.4'> reportsGetPastAHeldLock : ItemHighLevel {
            attribute :>> statement = "Once a failure report has begun, a line the
                kernel writes shall reach the console port after a bounded wait even
                when the port's lock is held and will never be released.";
            attribute :>> criterion = "A report begun while another context holds the
                port's lock for good reaches the port whole, after at most 10,000,000
                attempts at the lock, on each architecture, 3 of 3.";
            attribute :>> parent = ("O.FAILSAFE", "ASR-6");
        }
        // Added 2026-10-17 by panic-reboot (consultant ledger line 2143): the
        // N150 stop-gap, outside the reference configuration (ITEM.md §5).
        requirement <'H.FAIL.5'> resetAfterTheReportWhenAsked : ItemHighLevel {
            attribute :>> statement = "With ferrix.panic=reset read after stage 1's
                check, the first failure report shall, once its diagnostic and the
                reset line are on the port, in the pstore record and on the screen,
                wait 10 seconds on the free-running counter where its rate is known
                and reset the machine; with no value, halt, any other value, or in a
                report on another processor, it shall halt.";
            attribute :>> criterion = "In cargo xtask test-postmortem (x86-64 under
                KVM, AArch64): a boot with ferrix.onexit=panic ferrix.panic=reset
                prints the reset line and the loader's banner comes again at least 9.5
                s and at most 60 s later, quoting the panic; the same boot without the
                option and with ferrix.panic=Reset says it halts and prints no reset
                line.";
            attribute :>> parent = ("O.FAILSAFE", "ASR-6");
        }
        requirement <'H.FAIL.8'> machineChecksThatDoNotStop : ItemHighLevel {
            doc /* docs/MACHINE-CHECK.md (customer, 2026-10-30; consultant M10).
                H.FAIL.1 stops on every failed consistency check; these are the
                hardware errors that are not one: the kernel's own state is
                intact, and only a program's page or nothing at all is lost. */
            attribute :>> statement = "On x86-64 with recovery on, the kernel
                shall go on after a machine check only where every record is,
                by its vendor's rules (L.x86_64.233): on Intel's, corrected,
                uncorrected with no action required, action-optional with the
                interrupted code restartable, another processor's
                action-required record, or one action-required record a ring-3
                program consumed at a usable address; on AMD's and Hygon's,
                corrected, deferred, or one action-required record a ring-3
                program consumed with EIPV at a usable address where the
                processor reports SUCCOR, the program signalled, or ended where
                RIPV is clear or TCC set; on any other vendor's, corrected. It
                shall then retire the frame of each uncorrected record with a
                usable address (a deferred one only by PhysAddrV), never hand it
                out again, and end or signal that program -- a program whose
                restartable load consumed a clean cached page goes on unsignalled,
                as H.FAIL.11 says; a system call's copy that consumed poison goes
                on as H.FAIL.10 says; every other machine check stops as
                H.FAIL.1.";
            attribute :>> criterion = "L.x86_64.221-232, L.x86_64.249-253 and L.mm.91-92
                each verified; test-mce and its five recovery modes pass under KVM
                and TCG; test-mce-cmci's modes pass under TCG on QEMU with patch
                0008 (docs/MACHINE-CHECK-CMCI.md). test-mce-driver's Own, Kill and
                Bystander: a ring-3 driver that consumes poison ends alone, status
                135, its frame retired and left unread (docs/MACHINE-CHECK-DRIVER.md;
                devmgr's restart the evidence's environment)";
            attribute :>> parent = ("O.FAILSAFE", "ASR-6");
        }
        requirement <'H.FAIL.9'> theScrubberTouchesOnlyFreeMemory : ItemHighLevel {
            doc /* docs/RAM-SCRUBBER.md (customer, 2026-10-30, item 7; consultant NOT YET ledger 5045, OK IF ledger 5057). */
            attribute :>> statement = "The RAM scrubber shall touch no frame in use, make no
                allocation fail but for the window of one frame's test in
                which two requests of one order meet the last two free blocks
                of it, never halt the machine where the firmware reports that
                the memory corrects errors, and never take more than its share
                of the retired set; a frame that fails its pattern test twice
                shall not be handed out again.";
            attribute :>> criterion = "test-scrub on x86-64 and AArch64: a full sweep of free memory,
                no allocation failed, nothing tested while busy, the
                stand-down without the gate's override; ARMv7-A's stand-down;
                mm/check.rs's check_scrubber, run only where the scrubber
                itself runs; L.mm.101-108, L.x86_64.243, L.aarch64.68,
                L.armv7a.30, L.object.252 and L.syscall.24 each with its
                check (L.object.253 released unwritten, ledger 5140 (3)). An
                ECC machine whose firmware reports Other or Unknown is the
                SAFETY-MANUAL's residual.";
            attribute :>> parent = ("O.FAILSAFE", "ASR-6");
        }
        requirement <'H.FAIL.10'> aCopyThatConsumesPoisonFailsTheCall : ItemHighLevel {
            doc /* docs/MACHINE-CHECK-COPY.md (customer, 2026-10-30, machine-check item 2; consultant OK IF ledger 5216). */
            attribute :>> statement = "On x86-64 with recovery on, a system call's
                read of a program's memory that consumes poison shall end with
                the call failing (or, for a write that already stored the pages
                before it, ending short at that page), the frame retired and,
                where the memory is the
                caller's own and it has signals, SIGBUS BUS_MCEERR_AR at the
                page; the kernel shall resume only at the copy's own exit, never
                inside the copy past the poison, and stop in every other ring-0
                case it stops in under H.FAIL.8.";
            attribute :>> criterion = "test-mce-copy under KVM with AMD's records (the
                guest has SUCCOR), at one and two processors: the victim's write
                fails EFAULT or ends short at the poisoned page, its handler gets
                SIGBUS code 4 at the injected page's user address, the frame is
                retired and the kernel goes on; its modes stop where they must;
                the TCG rows and, on an AMD host, Intel's records are
                fail-closed rows only (TCG runs rep movsb in one step and
                reports no recovery; Intel's model has no MCG_SER_P there), so
                Intel's recovery is shown by stage 3's tables and frame;
                L.x86_64.244-246 and L.syscall.25-26 each with its check. test-mce-driver-copy: a driver's
                channel_write of its poisoned page fails, the driver ends with
                status 135";
            attribute :>> parent = ("O.FAILSAFE", "ASR-6");
        }
        requirement <'H.FAIL.12'> aBadFrameStaysOutAcrossAWarmReset : ItemHighLevel {
            doc /* docs/MACHINE-CHECK-RESTART.md slice 8a (customer, 2026-10-30, item 8; consultant OK IF ledger 5467, code OK IF ledger 5487). Arm has nothing that retires frames today. Residual: a table frame the boot info area or firmware holds by the time the loader reads the table is not kept out (said). TCG only; KVM injection across a reset not tried. A bad_frames = choice image (desktop, no claim; MACHINE-CHECK-RESTART §10, ledger 5579) gives it only with ferrix.badframes absent or persist. */
            attribute :>> statement = "In an image built bad_frames=persist, whatever its
                command line, after a warm reset, the kernel shall hand out no frame the
                boot before retired, nor the frame of an uncorrected record the
                machine check named, where the loader marked it left out (the
                assumption of use: the loader marks exactly the frames of the
                version-3 table, the banks and the event log's set, and never
                drops one).";
            attribute :>> criterion = "L.console.58-59, L.mm.109-110 and L.x86_64.254 each
                verified; test-mce-restart under TCG with Intel's records: a fatal
                record under ferrix.panic=reset, then boot 2's loader says boot 1
                ended in a machine check and keeps the page out (left and table),
                its kernel leaves the frame out and its poll finds it already
                retired; test-mce-restart-retired: a frame a recovered machine
                check retired kept out of boots 2 and 3 from the table alone. TCG
                only; KVM injection across a reset not tried; xtask check: the persist loader carries no
                ferrix.badframes on any architecture, the choice loader does.";
            attribute :>> parent = ("O.FAILSAFE", "ASR-6");
        }
        requirement <'H.FAIL.13'> aBadFrameStaysOutAcrossAPowerCycle : ItemHighLevel {
            doc /* docs/MACHINE-CHECK-RESTART.md §9, slice 8b (customer, 2026-10-30, item 8; consultant design OK IF ledger 5511). The kernel is unchanged: the loader (outside the item) keeps the set in the boot disk's event log and marks it left out (AoU-39). Residuals: a frame retired in a run that ended by a power cut or a power-off before any warm reset is not in the set; another boot disk or a reinstall starts with an empty set; an older writer (a loader or inspection tool from before 8b) drops the set on its first header write; a set frame firmware holds is not kept out (said); TCG only; nothing retires frames on Arm. A bad_frames = choice image (desktop, no claim; MACHINE-CHECK-RESTART §10, ledger 5579) gives it only with ferrix.badframes absent or persist. */
            attribute :>> statement = "In an image built bad_frames=persist, whatever its
                command line, after a power cycle, the kernel shall hand out no frame
                of the boot disk's event-log bad-frame set, where the loader marked
                it left out (AoU-39).";
            attribute :>> criterion = "L.mm.110 verified; test-mce-restart-power under TCG
                with Intel's records: a frame a recovered machine check retired is
                kept in the event log by boot 2's loader, kept out of a cold boot 3
                after a power cut from the log alone, nothing written by boots 3 and
                4, and gone from a cold boot 5 after the host's clear-bad-frames;
                an attempt whose victim page firmware holds at boot 2's table read
                or boot 3's log read (the loader's exact in-use line, the frame
                still in the log) is inconclusive and made again from a fresh
                disk, at most 3, all 3 inconclusive failing; with ferrix.badframes=off
                on the command line, ignored. xtask check: the persist loader carries
                no ferrix.badframes on any architecture, the choice loader does. TCG
                only.";
            attribute :>> parent = ("O.FAILSAFE", "ASR-6");
        }
        // Added 2026-11-08 by box-watchdog / crash-tools (consultant ledger
        // lines 7925, 8078): the N150 box's watchdog, outside the reference
        // configuration (ferrix.watchdog off).
        requirement <'H.FAIL.14'> aStarvedFeederIsReported : ItemHighLevel {
            doc /* docs/POSTMORTEM.md §6.11. Software only: the deadline is looked
                at by a kernel task, so a kernel that stops is not detected (the
                lockup detector, S4a, and the chipset's TCO are parked), and a
                report resets the machine only under ferrix.panic=reset. */
            attribute :>> statement = "With ferrix.watchdog=on, once a privileged
                program has opened /dev/watchdog, a timeout that passes with no
                feed while the kernel runs shall end in a failure report under
                FX-9008; a feed shall prove only that the feeder's own loop
                turned, and no feed, write or timeout shall arm a deadline that
                was disarmed.";
            attribute :>> criterion = "L.lockup.6-9 verified; test-watchdog's cases on
                x86-64 under KVM: a stopped and a killed feeder reported, a feed for
                four timeouts, a magic close, DISABLECARD, a halt, init's feed and the
                option off not reported.";
            attribute :>> parent = ("O.FAILSAFE", "ASR-6");
        }
        requirement <'H.FAIL.11'> aCleanCachedPageCostsADiskRead : ItemHighLevel {
            doc /* docs/MACHINE-CHECK-PAGECACHE.md (customer, 2026-10-30, machine-check item 3; consultant OK IF ledger 5294). */
            attribute :>> statement = "On x86-64 with recovery on, poison in a clean
                page-cache frame shall cost a disk read and nothing else: a read
                that consumes it refilled from the disk and answered, a program
                whose restartable load consumed it faulting the page in again
                without a signal, the poll dropping it first; a page that is not
                clean -- or a clean one held still at that moment by a write, a
                truncation, a writeback or a reclaim of its file -- shall never be
                dropped or refilled (its read fails EIO, its mapper is signalled
                as H.FAIL.8 says), and a frame that cannot be retired shall never
                be taken.";
            attribute :>> criterion = "test-mce-pagecache's read and mapped modes under
                KVM with AMD's records (the read answered with the disk's bytes,
                the mapper unsignalled), its dirty modes on a memfd's pages under
                KVM (the read failing EIO or ending short exactly at the poisoned
                page, the mapper SIGBUS), its poll mode with Intel's
                UCNA record under TCG (the page dropped before it is read), and
                test-mce-copy-file under KVM (the copy fails, SIGBUS, the page
                dropped), each frame retired; the TCG copy rows fail-closed only;
                stage 12's poison check (the dirty disk page among its cases);
                L.object.259-261 and L.x86_64.247-248 each with its check.";
            attribute :>> parent = ("O.FAILSAFE", "ASR-6");
        }
    }

    package Storage {
        doc /* The btrfs reader and write path, `ferrix-btrfs` and
             * `ferrix-btrfs-write`, in the item since 2026-10-02: O.MEDIA and
             * ASR-9 (FPT_TDC.1, FDP_SDI.2). Their interface below is the
             * `Device` and `WriteDevice` traits the kernel's block layer
             * answers, above it `Volume` and `WriteVolume`; the VFS glue on top
             * (`ferrix-btrfs-vfs`, src/kernel/src/fs/btrfs*.rs) is load, so
             * these promise what the two crates do at `Volume` and
             * `WriteVolume`, not what a program sees through a mount. The
             * low-level requirements are part 24. Some sit under a requirement
             * here by decomposition rather than as a case of its criterion:
             * L.btrfs.31 and .70 (a node's address and generation) refine
             * H.STORE.2, whose criterion tests a data sector, and L.btrfs.16
             * and .92 (superblock stripes) refine H.STORE.5, whose criterion
             * tests the trees' consistency. */

        requirement <'H.STORE.1'> untrustedVolumesAnswered : ItemHighLevel {
            attribute :>> statement = "The btrfs reader and writer shall answer
                every volume image, whatever its bytes, with a value or an error,
                without reading or writing outside a buffer, panicking or looping
                without bound.";
            attribute :>> criterion = "Each of 4,096 single-byte patches of a
                superblock, and of a leaf, parses or is refused, and every accessor of
                what parses answers, 0 panics. The decoders' own totality, and the
                `btrfs_read` fuzzer's resealed images, are their low-level
                requirements' and outside this criterion; the write path, which
                parses every node through the reader, has no hostile-image check of
                its own yet (TODO.md).";
            attribute :>> parent = "O.MEDIA";
        }
        requirement <'H.STORE.2'> damageNotReturnedAsData : ItemHighLevel {
            attribute :>> statement = "A block whose checksum disagrees with its
                contents shall never be returned as valid: the reader shall read
                another copy where the chunk keeps one, and otherwise answer an
                error.";
            attribute :>> criterion = "With the first copy of a DUP data sector damaged,
                a file read returns the file's bytes from the second; with both
                damaged, it answers DataChecksum and hands back none of the
                sector's bytes.";
            attribute :>> parent = ("O.MEDIA", "ASR-9");
        }
        requirement <'H.STORE.3'> aCommitIsAllOrNothing : ItemHighLevel {
            attribute :>> statement = "Until a commit's superblock is written, the
                volume on the device shall be exactly the last commit, whatever of
                the commit's other writes have reached it.";
            attribute :>> criterion = "500 inserts committed, and the commit's
                writes replayed without its superblocks onto the volume as it was, leave a volume
                that checks clean and holds exactly the last commit's items.";
            attribute :>> parent = "ASR-9";
        }
        requirement <'H.STORE.4'> promisesSurviveAPowerCut : ItemHighLevel {
            attribute :>> statement = "What a commit or a log commit returned success
                for shall be found, no older, when the volume is opened after a power
                cut at any later point, the log replayed if the superblock names
                one.";
            attribute :>> criterion = "Of 100 cuts over 4 random scenarios of writes,
                logs and commits, each rebuilt as the device may have left the disk,
                every one opens, checks clean down to free space and checksums, and
                rolls back no completed promise.";
            attribute :>> parent = "ASR-9";
        }
        requirement <'H.STORE.5'> nothingInUseIsHandedOut : ItemHighLevel {
            attribute :>> statement = "Each commit shall leave the extent tree, the
                block groups' usage, the free-space tree and the superblock's totals
                agreeing with the trees, so that no block in use is free.";
            attribute :>> criterion = "After 3,000 random edits on the blank
                fixture, committed as they go, the writer's checker finds every tree block's
                and data extent's references, each block group's usage and free
                space and the superblock's total consistent.";
            attribute :>> parent = "ASR-9";
        }
        requirement <'H.STORE.6'> aFullVolumeRefusesBeforeItChanges : ItemHighLevel {
            attribute :>> statement = "An operation the volume has no room for shall
                be refused with no space before it changes anything, leaving the
                transaction able to commit.";
            attribute :>> criterion = "On a 128 MiB volume, creates until its trees
                are full end in NoSpace with the transaction not aborted, its commit
                succeeds, and a deletion still makes room for another create.";
            attribute :>> parent = "ASR-9";
        }
        requirement <'H.STORE.7'> allocationFailureIsAnswered : ItemHighLevel {
            attribute :>> statement = "An allocation the btrfs writer cannot make shall
                be answered to its caller as an error, aborting the transaction if an
                edit had begun, and never as a panic or a stop of the element.";
            attribute :>> criterion = "With every allocation of the writer's
                operations failed in turn, each operation succeeds or answers an
                error, no panic is taken, and the volume reopened from the device is
                the last commit and checks clean.";
            attribute :>> parent = ("O.QUOTA", "ASR-9");
        }
        requirement <'H.STORE.8'> aFailedTransactionIsNeverCommitted : ItemHighLevel {
            attribute :>> statement = "An operation that fails after it changed
                something shall abort its transaction, so that none of it is
                committed, and the volume reloaded at its last commit shall take no
                further change.";
            attribute :>> criterion = "Through a mount, a commit whose device write
                fails answers EIO; the mount then reads the last commit, has no
                trace of the aborted transaction, answers EROFS to a write, a
                truncation and a create, and the disk holds the last commit.";
            attribute :>> parent = "ASR-9";
        }
        requirement <'H.DEV.12'> deviceAuthorityFromTheKernelDirectly : ItemHighLevel {
            attribute :>> statement = "Under personality=user, device authority and a safety partition's
                authority shall pass from the kernel to their holders directly, and a
                safety partition's device shall reach no other holder.";
            attribute :>> criterion = "test-first-processes: a described device goes to the manager and is
                kept from devmgr; a description naming no node, or malformed, stops
                the boot; L.object.322, 323.";
            attribute :>> parent = ("O.CAPABILITY", "ASR-3");
        }
        requirement <'H.DEV.13'> eachFirstProcessEndsSafely : ItemHighLevel {
            attribute :>> statement = "Each first process's death shall leave nothing running on its
                authority: the manager's is the machine's safe state, devmgr's kills
                its drivers and quiesces their devices, linuxd's kills its programs.
                This family stands in H.DEV because the block holds no H.OBJ.";
            attribute :>> criterion = "test-first-processes' deaths; L.object.326, 327, 328.";
            attribute :>> parent = ("O.CAPABILITY", "ASR-3");
        }
    }
}
